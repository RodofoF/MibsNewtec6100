NEWTEC-MULTI-DEMOD-MIB DEFINITIONS ::= BEGIN

IMPORTS
    Unsigned32,
    Integer32,
    Counter32,
    MODULE-IDENTITY,
    OBJECT-IDENTITY,
    OBJECT-TYPE
        FROM SNMPv2-SMI

    MODULE-COMPLIANCE,
    OBJECT-GROUP
        FROM SNMPv2-CONF
    
    Float32TC
        FROM FLOAT-TC-MIB

    NtcAlarmState,
    NtcEnable
        FROM NEWTEC-TC-MIB

    DisplayString
        FROM SNMPv2-TC

    ntcFunction
        FROM NEWTEC-MAIN-MIB;


--
--  Module Identification
--

ntcMultiDemodulator   MODULE-IDENTITY
    LAST-UPDATED "201602011100Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular DVB multi-demodulator MIB containing definitions for DVB-S2 and
        S2-Extensions and newer demodulator functionality."

    REVISION  "201602011100Z"
    DESCRIPTION
        "Monitoring columns added in ntcMultiDemodMon Table"
    REVISION  "201509251100Z"
    DESCRIPTION
        "Automatic NonLinear PostCompensation added"
    REVISION  "201502190900Z"
    DESCRIPTION
        "Support for external converter"
    REVISION  "201502040800Z"
    DESCRIPTION
        "ntcMultiDemodCfgStreamMode description adapted"
    REVISION  "201411241200Z"
    DESCRIPTION
        "ntcMultiDemodStatsPacketErrRatio description adapted"
    REVISION  "201410310800Z"
    DESCRIPTION
        "ntcMultiDemodCfgMode enumerations extended"
    REVISION  "201409230700Z"
    DESCRIPTION
        "Descriptions of ntcMultiDemodBuCarMon and ntcMultiDemodBuCarCfg adapted"
    REVISION  "201409041200Z"
    DESCRIPTION
        "BackupCarrier feature added."
    REVISION  "201407080900Z"
    DESCRIPTION
        "dvbs2x addition"
    REVISION  "201402031200Z"
    DESCRIPTION
        "Added acquisition range, equalink client, new transponder operation mode"
    REVISION  "201310161200Z"
    DESCRIPTION
        "M&C parameters added for MDM6100 R2.0"
    REVISION  "201309230800Z"
    DESCRIPTION
        "Alarms Status as Textual Conventions"
    REVISION  "201308210600Z"
    DESCRIPTION
        "AlarmBufferOverflow added"
    REVISION  "201307050600Z"
    DESCRIPTION
        "Some defaults changed"
    REVISION  "201306251200Z"
    DESCRIPTION
        "Initial release for MDM6000 R1.1"
    ::= { ntcFunction  3300 }
    

--
-- Top-Level Structure
--

-- ntcMultiDemodulator content

ntcMultiDemodObjects             OBJECT-IDENTITY
    STATUS        current
    DESCRIPTION   "Container holding ntcMultiDemodObjects definitions."
    ::= { ntcMultiDemodulator 1 }
    
ntcMultiDemodConformance         OBJECT-IDENTITY
    STATUS        current
    DESCRIPTION   "Conformance requirements."
    ::= { ntcMultiDemodulator 2 }
    
-- ntcMultiDemodObjects content

ntcMultiDemodAlarm               OBJECT-IDENTITY
    STATUS        current
    DESCRIPTION   "Container holding ntcMultiDemodAlarm definitions."
    ::= { ntcMultiDemodObjects 1 }
    
ntcMultiDemodCmCfg               OBJECT-IDENTITY
    STATUS        current
    DESCRIPTION   "Container holding ntcMultiDemodCmCfg definitions."
    ::= { ntcMultiDemodObjects 7 }
    
ntcMultiDemodCmMon               OBJECT-IDENTITY
    STATUS        current
    DESCRIPTION   "Container holding ntcMultiDemodCmMon definitions."
    ::= { ntcMultiDemodObjects 8 }
    
ntcMultiDemodCmConv              OBJECT-IDENTITY
    STATUS        current
    DESCRIPTION   "Container holding ntcMultiDemodCmConv definitions."
    ::= { ntcMultiDemodObjects 14 }
    
-- ntcMultiDemodConformance content

ntcMultiDemodConfCompliance      OBJECT-IDENTITY
    STATUS        current
    DESCRIPTION   "Device compliance statements."
    ::= { ntcMultiDemodConformance 1 }
    
ntcMultiDemodConfGroup           OBJECT-IDENTITY
    STATUS        current
    DESCRIPTION   "Groups used by device compliance statements."
    ::= { ntcMultiDemodConformance 2 }
    

--
-- Managed Objects
--

ntcMultiDemodAlmGeneralDemod     OBJECT-TYPE
    SYNTAX      NtcAlarmState
    MAX-ACCESS  read-only
    STATUS      current
    DESCRIPTION
        "This alarm is raised when there is a general Demodulator alarm. This variable
        indicates the current status of the alarm."
    ::= { ntcMultiDemodAlarm 1 }
    
ntcMultiDemodAlmInternalError    OBJECT-TYPE
    SYNTAX      NtcAlarmState
    MAX-ACCESS  read-only
    STATUS      current
    DESCRIPTION
        "This alarm is raised when there is a internal error Demodulator alarm. This
        variable indicates the current status of the alarm."
    ::= { ntcMultiDemodAlarm 2 }
    
ntcMultiDemodAlmInputSaturated   OBJECT-TYPE
    SYNTAX      NtcAlarmState
    MAX-ACCESS  read-only
    STATUS      current
    DESCRIPTION
        "This alarm indicates that the L-band input power is too high This variable
        indicates the current status of the alarm."
    ::= { ntcMultiDemodAlarm 3 }
    
ntcMultiDemodAlmNoLock           OBJECT-TYPE
    SYNTAX      NtcAlarmState
    MAX-ACCESS  read-only
    STATUS      current
    DESCRIPTION
        "This alarm is raised when the demodulator cannot lock on the received carrier
        This variable indicates the current status of the alarm."
    ::= { ntcMultiDemodAlarm 4 }
    
ntcMultiDemodAlmLnbPowerControl  OBJECT-TYPE
    SYNTAX      NtcAlarmState
    MAX-ACCESS  read-only
    STATUS      current
    DESCRIPTION
        "This alarm is raised when an error occurs in the LNB power supply. This
        variable indicates the current status of the alarm."
    ::= { ntcMultiDemodAlarm 5 }
    
ntcMultiDemodAlmDecoderOvrload   OBJECT-TYPE
    SYNTAX      NtcAlarmState
    MAX-ACCESS  read-only
    STATUS      current
    DESCRIPTION
        "This alarm is raised when the decoder is overloaded This variable indicates
        the current status of the alarm."
    ::= { ntcMultiDemodAlarm 6 }
    
ntcMultiDemodAlmNoPlLock         OBJECT-TYPE
    SYNTAX      NtcAlarmState
    MAX-ACCESS  read-only
    STATUS      current
    DESCRIPTION
        "This alarm indicates that the demodulator cannot lock to the physical layer
        headers This variable indicates the current status of the alarm."
    ::= { ntcMultiDemodAlarm 7 }
    
ntcMultiDemodAlmBufferOverflow   OBJECT-TYPE
    SYNTAX      NtcAlarmState
    MAX-ACCESS  read-only
    STATUS      current
    DESCRIPTION
        "This alarm is raised when the demodulator encoutered an internal buffer
        overflow This variable indicates the current status of the alarm."
    ::= { ntcMultiDemodAlarm 8 }
    
ntcMultiDemodAlarmStateTable     OBJECT-TYPE
    SYNTAX      SEQUENCE OF NtcMultiDemodAlarmStateEntry
    MAX-ACCESS  not-accessible
    STATUS      current
    DESCRIPTION
        "Alarm Status Table"
    ::= { ntcMultiDemodObjects 2 }

ntcMultiDemodAlarmStateEntry     OBJECT-TYPE
    SYNTAX      NtcMultiDemodAlarmStateEntry
    MAX-ACCESS  not-accessible
    STATUS      current
    DESCRIPTION
        "A conceptual row of the ntcMultiDemodAlarmStateTable."
    INDEX   { ntcMultiDemodASDemodId  }
    ::= { ntcMultiDemodAlarmStateTable 1 }

NtcMultiDemodAlarmStateEntry     ::= SEQUENCE {
    ntcMultiDemodASDemodId              INTEGER,
    ntcMultiDemodASGeneralDemod         NtcAlarmState,
    ntcMultiDemodASInternalError        NtcAlarmState,
    ntcMultiDemodASInputSaturated       NtcAlarmState,
    ntcMultiDemodASNoPlLock             NtcAlarmState,
    ntcMultiDemodASNoLock               NtcAlarmState,
    ntcMultiDemodASLnbPowerControl      NtcAlarmState,
    ntcMultiDemodASDecoderOverloaded    NtcAlarmState
    }
    
ntcMultiDemodASDemodId           OBJECT-TYPE
    SYNTAX      INTEGER { demod1(1), demod2(2), demod3(3) }
    MAX-ACCESS  not-accessible
    STATUS      current
    DESCRIPTION
        "The id of the demodulator"
    ::= { ntcMultiDemodAlarmStateEntry 1 }
    
ntcMultiDemodASGeneralDemod      OBJECT-TYPE
    SYNTAX      NtcAlarmState
    MAX-ACCESS  read-only
    STATUS      current
    DESCRIPTION
        "This alarm is raised when there is a general Demodulator alarm. This variable
        indicates the current status of the alarm."
    ::= { ntcMultiDemodAlarmStateEntry 2 }
    
ntcMultiDemodASInternalError     OBJECT-TYPE
    SYNTAX      NtcAlarmState
    MAX-ACCESS  read-only
    STATUS      current
    DESCRIPTION
        "This alarm is raised when there is a internal error Demodulator alarm. This
        variable indicates the current status of the alarm."
    ::= { ntcMultiDemodAlarmStateEntry 3 }
    
ntcMultiDemodASInputSaturated    OBJECT-TYPE
    SYNTAX      NtcAlarmState
    MAX-ACCESS  read-only
    STATUS      current
    DESCRIPTION
        "This alarm indicates that the L-band input power is too high This variable
        indicates the current status of the alarm."
    ::= { ntcMultiDemodAlarmStateEntry 4 }
    
ntcMultiDemodASNoPlLock          OBJECT-TYPE
    SYNTAX      NtcAlarmState
    MAX-ACCESS  read-only
    STATUS      current
    DESCRIPTION
        "This alarm indicates that the demodulator cannot lock to the physical layer
        headers This variable indicates the current status of the alarm."
    ::= { ntcMultiDemodAlarmStateEntry 5 }
    
ntcMultiDemodASNoLock            OBJECT-TYPE
    SYNTAX      NtcAlarmState
    MAX-ACCESS  read-only
    STATUS      current
    DESCRIPTION
        "This alarm is raised when the demodulator cannot lock on the received carrier
        This variable indicates the current status of the alarm."
    ::= { ntcMultiDemodAlarmStateEntry 6 }
    
ntcMultiDemodASLnbPowerControl   OBJECT-TYPE
    SYNTAX      NtcAlarmState
    MAX-ACCESS  read-only
    STATUS      current
    DESCRIPTION
        "This alarm is raised when an error occurs in the LNB power supply. This
        variable indicates the current status of the alarm."
    ::= { ntcMultiDemodAlarmStateEntry 7 }
    
ntcMultiDemodASDecoderOverloaded OBJECT-TYPE
    SYNTAX      NtcAlarmState
    MAX-ACCESS  read-only
    STATUS      current
    DESCRIPTION
        "This alarm is raised when the decoder is overloaded This variable indicates
        the current status of the alarm."
    ::= { ntcMultiDemodAlarmStateEntry 8 }
    
ntcMultiDemodCfgTable            OBJECT-TYPE
    SYNTAX      SEQUENCE OF NtcMultiDemodCfgEntry
    MAX-ACCESS  not-accessible
    STATUS      current
    DESCRIPTION
        "The configuration table."
    ::= { ntcMultiDemodObjects 3 }

ntcMultiDemodCfgEntry            OBJECT-TYPE
    SYNTAX      NtcMultiDemodCfgEntry
    MAX-ACCESS  not-accessible
    STATUS      current
    DESCRIPTION
        "A conceptual row of the ntcMultiDemodCfgTable."
    INDEX   { ntcMultiDemodCfgDemodId  }
    ::= { ntcMultiDemodCfgTable 1 }

NtcMultiDemodCfgEntry            ::= SEQUENCE {
    ntcMultiDemodCfgDemodId           INTEGER,
    ntcMultiDemodCfgEnable            NtcEnable,
    ntcMultiDemodCfgMode              INTEGER,
    ntcMultiDemodCfgInputFrequency    Unsigned32,
    ntcMultiDemodCfgSymbolRate        Unsigned32,
    ntcMultiDemodCfgRollOff           INTEGER,
    ntcMultiDemodCfgInputSelection    INTEGER,
    ntcMultiDemodCfgSpectralInv       INTEGER,
    ntcMultiDemodCfgPlScrambSig       Unsigned32,
    ntcMultiDemodCfgLnbPowerSupply    INTEGER,
    ntcMultiDemodCfgHardwareId        DisplayString,
    ntcMultiDemodCfgModCodDvbs        INTEGER,
    ntcMultiDemodCfgStreamMode        INTEGER,
    ntcMultiDemodCfgInterfaceRate     Unsigned32,
    ntcMultiDemodCfgAcqRange          Unsigned32,
    ntcMultiDemodCfgPlhdrScramSeq     Unsigned32,
    ntcMultiDemodCfgRfFrequency       DisplayString,
    ntcMultiDemodCfgModCodAmcDl       INTEGER
    }
    
ntcMultiDemodCfgDemodId          OBJECT-TYPE
    SYNTAX      INTEGER { demod1(1), demod2(2), demod3(3) }
    MAX-ACCESS  not-accessible
    STATUS      current
    DESCRIPTION
        "The id of the demodulator"
    ::= { ntcMultiDemodCfgEntry 1 }
    
ntcMultiDemodCfgEnable           OBJECT-TYPE
    SYNTAX      NtcEnable
    MAX-ACCESS  read-write
    STATUS      current
    DESCRIPTION
        "Enable or disable the demodulator function"
    DEFVAL { on }
    ::= { ntcMultiDemodCfgEntry 2 }
    
ntcMultiDemodCfgMode             OBJECT-TYPE
    SYNTAX      INTEGER { dvbs(0), dvbs2(1), s2ext(3), turbo(4), amcdvbs(5), amcnbc(6), dvbs2x(7), amcdl(8) }
    MAX-ACCESS  read-write
    STATUS      current
    DESCRIPTION
        "The modulation standard defines the operating mode of the demodulator.
        - DVB-S : compatible with DVB-S/DVB-DSNG modulation
        - DVB-S2 : compatible with EN302307
        - S2 Extensions : Newtec proprietary modulation to improve DVB-S2"
    DEFVAL { dvbs2 }
    ::= { ntcMultiDemodCfgEntry 3 }
    
ntcMultiDemodCfgInputFrequency   OBJECT-TYPE
    SYNTAX      Unsigned32
    UNITS       "Hz"
    MAX-ACCESS  read-write
    STATUS      current
    DESCRIPTION
        "Demodulator input frequency setting. Current devices support a frequency range
        of 950000000 to 2150000000 Hz."
    DEFVAL { 2000000000 }
    ::= { ntcMultiDemodCfgEntry 4 }
    
ntcMultiDemodCfgSymbolRate       OBJECT-TYPE
    SYNTAX      Unsigned32
    UNITS       "baud"
    MAX-ACCESS  read-write
    STATUS      current
    DESCRIPTION
        "Symbol rate of the received carrier"
    DEFVAL { 10000000 }
    ::= { ntcMultiDemodCfgEntry 5 }
    
ntcMultiDemodCfgRollOff          OBJECT-TYPE
    SYNTAX      INTEGER { auto(0), rolloff5(1), rolloff10(2), rolloff15(3), rolloff20(4), rolloff25(5), rolloff35(6) }
    MAX-ACCESS  read-write
    STATUS      current
    DESCRIPTION
        "The receive filter Roll-off factor setting determines the spectrum excess
        bandwidth by controlling the RCRO (Root Cosine Roll-off) factor of the matched
        filter at the demodulator input. The lower the Roll-off factor the higher the
        throughput. Note that increasing the throughput (higher symbolrate) requires
        more power from the satellite or it will result in a lower carrier-to-noise."
    DEFVAL { rolloff20 }
    ::= { ntcMultiDemodCfgEntry 6 }
    
ntcMultiDemodCfgInputSelection   OBJECT-TYPE
    SYNTAX      INTEGER { lbandRxA(0), lbandRxB(1), ifRx(3) }
    MAX-ACCESS  read-write
    STATUS      current
    DESCRIPTION
        "Toggle the demodulator input between L-BAND Rx A/B or IF Rx"
    DEFVAL { lbandRxA }
    ::= { ntcMultiDemodCfgEntry 7 }
    
ntcMultiDemodCfgSpectralInv      OBJECT-TYPE
    SYNTAX      INTEGER { direct(0), inverted(1), automatic(2) }
    MAX-ACCESS  read-write
    STATUS      current
    DESCRIPTION
        "Spectral inversion"
    DEFVAL { automatic }
    ::= { ntcMultiDemodCfgEntry 8 }
    
ntcMultiDemodCfgPlScrambSig      OBJECT-TYPE
    SYNTAX      Unsigned32
    MAX-ACCESS  read-write
    STATUS      current
    DESCRIPTION
        "The physical layer scrambler signature."
    DEFVAL { 0 }
    ::= { ntcMultiDemodCfgEntry 9 }
    
ntcMultiDemodCfgLnbPowerSupply   OBJECT-TYPE
    SYNTAX      INTEGER { none(0), e13V0kHz(1), e13V22kHz(2), e18V0kHz(3), e18V22kHz(4) }
    MAX-ACCESS  read-write
    STATUS      current
    DESCRIPTION
        "LNB Power Supply and Tone selection."
    DEFVAL { none }
    ::= { ntcMultiDemodCfgEntry 10 }
    
ntcMultiDemodCfgHardwareId       OBJECT-TYPE
    SYNTAX      DisplayString (SIZE(0..50))
    MAX-ACCESS  read-only
    STATUS      current
    DESCRIPTION
        "Demodulator hardware identification."
    ::= { ntcMultiDemodCfgEntry 11 }
    
ntcMultiDemodCfgModCodDvbs       OBJECT-TYPE
    SYNTAX      INTEGER { qpsk12(1), qpsk23(2), qpsk34(3), qpsk56(4), qpsk67(5), qpsk78(6), e8psk23(7), e8psk56(8), e8psk89(9), e16qam34(10), e16qam78(11) }
    MAX-ACCESS  read-write
    STATUS      current
    DESCRIPTION
        "The selection of the FEC code-rate and modulation scheme supported by DVB-S"
    DEFVAL { qpsk34 }
    ::= { ntcMultiDemodCfgEntry 12 }
    
ntcMultiDemodCfgStreamMode       OBJECT-TYPE
    SYNTAX      INTEGER { multistream(1), singlestream(2) }
    MAX-ACCESS  read-write
    STATUS      current
    DESCRIPTION
        "Specify if more than one input stream is multiplexed into the modulator or
        not. This sometimes impacts receiver compatibility."
    DEFVAL { multistream }
    ::= { ntcMultiDemodCfgEntry 13 }
    
ntcMultiDemodCfgInterfaceRate    OBJECT-TYPE
    SYNTAX      Unsigned32
    UNITS       "bps"
    MAX-ACCESS  read-only
    STATUS      current
    DESCRIPTION
        "Calculated Interface Rate"
    ::= { ntcMultiDemodCfgEntry 14 }
    
ntcMultiDemodCfgAcqRange         OBJECT-TYPE
    SYNTAX      Unsigned32
    UNITS       "Hz"
    MAX-ACCESS  read-write
    STATUS      current
    DESCRIPTION
        "Demodulator acquisition range. Actual applied range limited to 150% of
        symbolrate.."
    DEFVAL { 1000000 }
    ::= { ntcMultiDemodCfgEntry 15 }
    
ntcMultiDemodCfgPlhdrScramSeq    OBJECT-TYPE
    SYNTAX      Unsigned32 (0..2000)
    MAX-ACCESS  read-write
    STATUS      current
    DESCRIPTION
        "Physical layer scrambling sequence key"
    DEFVAL { 0 }
    ::= { ntcMultiDemodCfgEntry 16 }
    
ntcMultiDemodCfgRfFrequency      OBJECT-TYPE
    SYNTAX      DisplayString (SIZE(0..20))
    UNITS       "Hz"
    MAX-ACCESS  read-write
    STATUS      current
    DESCRIPTION
        "RF frequency"
    DEFVAL { "0" }
    ::= { ntcMultiDemodCfgEntry 17 }
    
ntcMultiDemodCfgModCodAmcDl      OBJECT-TYPE
    SYNTAX      INTEGER { qpsk12(1), qpsk23(2), qpsk67(3) }
    MAX-ACCESS  read-write
    STATUS      current
    DESCRIPTION
        "The selection of the FEC code-rate and modulation scheme supported by AMC-DL"
    DEFVAL { qpsk12 }
    ::= { ntcMultiDemodCfgEntry 18 }
    
ntcExtMultiDemodCfgTable         OBJECT-TYPE
    SYNTAX      SEQUENCE OF NtcExtMultiDemodCfgEntry
    MAX-ACCESS  not-accessible
    STATUS      current
    DESCRIPTION
        "The Extended configuration table."
    ::= { ntcMultiDemodObjects 4 }

ntcExtMultiDemodCfgEntry         OBJECT-TYPE
    SYNTAX      NtcExtMultiDemodCfgEntry
    MAX-ACCESS  not-accessible
    STATUS      current
    DESCRIPTION
        "A conceptual row of the ntcExtMultiDemodCfgTable."
    INDEX   { ntcExtMultiDemodCfgDemodId  }
    ::= { ntcExtMultiDemodCfgTable 1 }

NtcExtMultiDemodCfgEntry         ::= SEQUENCE {
    ntcExtMultiDemodCfgDemodId    INTEGER,
    ntcExtMultiDemodCfgOpMode     INTEGER
    }
    
ntcExtMultiDemodCfgDemodId       OBJECT-TYPE
    SYNTAX      INTEGER { demod1(1), demod2(2), demod3(3) }
    MAX-ACCESS  not-accessible
    STATUS      current
    DESCRIPTION
        "The id of the demodulator"
    ::= { ntcExtMultiDemodCfgEntry 1 }
    
ntcExtMultiDemodCfgOpMode        OBJECT-TYPE
    SYNTAX      INTEGER { single(1), multiple(2), singlelin(3) }
    MAX-ACCESS  read-write
    STATUS      current
    DESCRIPTION
        "Transponder Operation Mode selection."
    DEFVAL { multiple }
    ::= { ntcExtMultiDemodCfgEntry 2 }
    
ntcMultiDemodMonTable            OBJECT-TYPE
    SYNTAX      SEQUENCE OF NtcMultiDemodMonEntry
    MAX-ACCESS  not-accessible
    STATUS      current
    DESCRIPTION
        "The Monitoring table."
    ::= { ntcMultiDemodObjects 5 }

ntcMultiDemodMonEntry            OBJECT-TYPE
    SYNTAX      NtcMultiDemodMonEntry
    MAX-ACCESS  not-accessible
    STATUS      current
    DESCRIPTION
        "A conceptual row of the ntcMultiDemodMonTable."
    INDEX   { ntcMultiDemodMonDemodId  }
    ::= { ntcMultiDemodMonTable 1 }

NtcMultiDemodMonEntry            ::= SEQUENCE {
    ntcMultiDemodMonDemodId             INTEGER,
    ntcMultiDemodMonLbandInputLvl       Integer32,
    ntcMultiDemodMonCarrierInputLvl     Integer32,
    ntcMultiDemodMonEsNo                Integer32,
    ntcMultiDemodMonPhaseNoiseIndic     Float32TC,
    ntcMultiDemodMonOffRefMask          Integer32,
    ntcMultiDemodMonNonLinIndic         Integer32,
    ntcMultiDemodMonSymbolRate          Unsigned32,
    ntcMultiDemodMonCarrierOffset       Float32TC,
    ntcMultiDemodMonFrameCounter        Counter32,
    ntcMultiDemodMonDummyFrameCtr       Counter32,
    ntcMultiDemodMonErroredFrameCtr     Counter32,
    ntcMultiDemodMonCycleSlipCtr        Counter32,
    ntcMultiDemodMonLastModCod          INTEGER,
    ntcMultiDemodModCodStatsReset       INTEGER,
    ntcMultiDemodMonVber                Integer32,
    ntcMultiDemodMonBer                 Integer32,
    ntcMultiDemodMonEbNo                Integer32,
    ntcMultiDemodMonLinkMargin          Integer32,
    ntcMultiDemodMonOperationalState    INTEGER,
    ntcMultiDemodMonLastNonDumModCod    INTEGER,
    ntcMultiDemodMonRollOff             INTEGER,
    ntcMultiDemodMonQefM                Integer32,
    ntcMultiDemodMonSpectralInv         INTEGER,
    ntcMultiDemodMonVberClp             INTEGER,
    ntcMultiDemodMonBerClp              INTEGER,
    ntcMultiDemodMonQefMClp             INTEGER,
    ntcMultiDemodMonEbNoClp             INTEGER
    }
    
ntcMultiDemodMonDemodId          OBJECT-TYPE
    SYNTAX      INTEGER { demod1(1), demod2(2), demod3(3) }
    MAX-ACCESS  not-accessible
    STATUS      current
    DESCRIPTION
        "The id of the demodulator"
    ::= { ntcMultiDemodMonEntry 1 }
    
ntcMultiDemodMonLbandInputLvl    OBJECT-TYPE
    SYNTAX      Integer32 (-1000..500)
    UNITS       "dBm"
    MAX-ACCESS  read-only
    STATUS      current
    DESCRIPTION
        "Input level measured on the full L-band range. A value of
        -1000 indicates that the measurement is unreliably low."
    ::= { ntcMultiDemodMonEntry 2 }
    
ntcMultiDemodMonCarrierInputLvl  OBJECT-TYPE
    SYNTAX      Integer32 (-1000..500)
    UNITS       "dBm"
    MAX-ACCESS  read-only
    STATUS      current
    DESCRIPTION
        "Input level measured on the selected carrier"
    ::= { ntcMultiDemodMonEntry 3 }
    
ntcMultiDemodMonEsNo             OBJECT-TYPE
    SYNTAX      Integer32 (-1000..3000)
    UNITS       "dB"
    MAX-ACCESS  read-only
    STATUS      current
    DESCRIPTION
        "Received Es/No Header"
    ::= { ntcMultiDemodMonEntry 4 }
    
ntcMultiDemodMonPhaseNoiseIndic  OBJECT-TYPE
    SYNTAX      Float32TC
    UNITS       "deg."
    MAX-ACCESS  read-only
    STATUS      current
    DESCRIPTION
        "PhaseNoiseIndication"
    ::= { ntcMultiDemodMonEntry 5 }
    
ntcMultiDemodMonOffRefMask       OBJECT-TYPE
    SYNTAX      Integer32 (-1000..500)
    UNITS       "dB"
    MAX-ACCESS  read-only
    STATUS      current
    DESCRIPTION
        "Offset To Reference Mask"
    ::= { ntcMultiDemodMonEntry 6 }
    
ntcMultiDemodMonNonLinIndic      OBJECT-TYPE
    SYNTAX      Integer32 (-100..100)
    UNITS       "%"
    MAX-ACCESS  read-only
    STATUS      current
    DESCRIPTION
        "This value gives an indication of the non-linearity of the carrier"
    ::= { ntcMultiDemodMonEntry 7 }
    
ntcMultiDemodMonSymbolRate       OBJECT-TYPE
    SYNTAX      Unsigned32
    UNITS       "baud"
    MAX-ACCESS  read-only
    STATUS      current
    DESCRIPTION
        "Tracked Symbol Rate of the received carrier"
    ::= { ntcMultiDemodMonEntry 8 }
    
ntcMultiDemodMonCarrierOffset    OBJECT-TYPE
    SYNTAX      Float32TC
    UNITS       "Hz"
    MAX-ACCESS  read-only
    STATUS      current
    DESCRIPTION
        "CarrierOffset"
    ::= { ntcMultiDemodMonEntry 9 }
    
ntcMultiDemodMonFrameCounter     OBJECT-TYPE
    SYNTAX      Counter32
    UNITS       "frames"
    MAX-ACCESS  read-only
    STATUS      current
    DESCRIPTION
        "Frame counter"
    ::= { ntcMultiDemodMonEntry 10 }
    
ntcMultiDemodMonDummyFrameCtr    OBJECT-TYPE
    SYNTAX      Counter32
    UNITS       "frames"
    MAX-ACCESS  read-only
    STATUS      current
    DESCRIPTION
        "Dummy PL frame counter"
    ::= { ntcMultiDemodMonEntry 11 }
    
ntcMultiDemodMonErroredFrameCtr  OBJECT-TYPE
    SYNTAX      Counter32
    UNITS       "frames"
    MAX-ACCESS  read-only
    STATUS      current
    DESCRIPTION
        "Errored frame counter"
    ::= { ntcMultiDemodMonEntry 12 }
    
ntcMultiDemodMonCycleSlipCtr     OBJECT-TYPE
    SYNTAX      Counter32
    UNITS       "frames"
    MAX-ACCESS  read-only
    STATUS      current
    DESCRIPTION
        "Cycle Slip counter"
    ::= { ntcMultiDemodMonEntry 13 }
    
ntcMultiDemodMonLastModCod       OBJECT-TYPE
    SYNTAX      INTEGER { dummy(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215), qpsk1345(256), qpsk920(257), qpsk1120(258), e8apsk59l(259), e8apsk2645l(260), e8psk2336(261), e8psk2536(262), e8psk1318(263), e16apsk12l(264), e16apsk815l(265), e16apsk59l(266), e16apsk2645(267), e16apsk35(268), e16apsk35l(269), e16apsk2845(270), e16apsk2336(271), e16apsk23l(272), e16apsk2536(273), e16apsk1318(274), e16apsk79(275), e16apsk7790(276), e32apsk23l(277), e32apsk3245(278), e32apsk1115(279), e32apsk79(280), e64apsk3245l(281), e64apsk1115(282), e64apsk79(283), e64apsk45(284), e64apsk56(285), e128apsk34(286), e128apsk79(287), e256apsk2945l(288), e256apsk23l(289), e256apsk3145l(290), e256apsk3245(291), e256apsk1115l(292), e256apsk34(293), qpsk1145(294), qpsk415(295), qpsk1445(296), qpsk715(297), qpsk815(298), qpsk3245(299), e8psk715(300), e8psk815(301), e8psk2645(302), e8psk3245(303), e16apsk715(304), e16apsk815(305), e16apsk3245(306), e32apsk23(307) }
    MAX-ACCESS  read-only
    STATUS      current
    DESCRIPTION
        "The most recently seen MODCOD"
    ::= { ntcMultiDemodMonEntry 14 }
    
ntcMultiDemodModCodStatsReset    OBJECT-TYPE
    SYNTAX      INTEGER { counting(0), reset(1) }
    MAX-ACCESS  read-write
    STATUS      current
    DESCRIPTION
        "Reset MODCOD statistics"
    DEFVAL { counting }
    ::= { ntcMultiDemodMonEntry 15 }
    
ntcMultiDemodMonVber             OBJECT-TYPE
    SYNTAX      Integer32 (0..1000000)
    MAX-ACCESS  read-only
    STATUS      current
    DESCRIPTION
        "Viterbi Bit Error Rate"
    ::= { ntcMultiDemodMonEntry 16 }
    
ntcMultiDemodMonBer              OBJECT-TYPE
    SYNTAX      Integer32 (0..1000000)
    MAX-ACCESS  read-only
    STATUS      current
    DESCRIPTION
        "The estimated bit error rate of the output data."
    ::= { ntcMultiDemodMonEntry 17 }
    
ntcMultiDemodMonEbNo             OBJECT-TYPE
    SYNTAX      Integer32 (0..2500)
    UNITS       "dB"
    MAX-ACCESS  read-only
    STATUS      current
    DESCRIPTION
        "Received Eb/No"
    ::= { ntcMultiDemodMonEntry 18 }
    
ntcMultiDemodMonLinkMargin       OBJECT-TYPE
    SYNTAX      Integer32 (-500..2500)
    UNITS       "dB"
    MAX-ACCESS  read-only
    STATUS      current
    DESCRIPTION
        "Link margin"
    ::= { ntcMultiDemodMonEntry 19 }
    
ntcMultiDemodMonOperationalState OBJECT-TYPE
    SYNTAX      INTEGER { operational(0), failed(1), offduty(2), dependent(3) }
    MAX-ACCESS  read-only
    STATUS      current
    DESCRIPTION
        "Identify the actual operational state of the component instance
        - Operational: Component instance ready for use
        - Failed: The component instance has 1 or more alarms which effect the proper
        function of the component
        - OffDuty: The component instance has a connection to another component
        instance, but that instance is not active. A good example of this is our
        Demod, which is a provider of TS or BBF instances, but only 1 type of
        instances are allowed at the same time.
        - Dependent: This means that the current component instance is linked with
        another component instance which is in alarm."
    ::= { ntcMultiDemodMonEntry 20 }
    
ntcMultiDemodMonLastNonDumModCod OBJECT-TYPE
    SYNTAX      INTEGER { unknown(0), qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215), qpsk1345(256), qpsk920(257), qpsk1120(258), e8apsk59l(259), e8apsk2645l(260), e8psk2336(261), e8psk2536(262), e8psk1318(263), e16apsk12l(264), e16apsk815l(265), e16apsk59l(266), e16apsk2645(267), e16apsk35(268), e16apsk35l(269), e16apsk2845(270), e16apsk2336(271), e16apsk23l(272), e16apsk2536(273), e16apsk1318(274), e16apsk79(275), e16apsk7790(276), e32apsk23l(277), e32apsk3245(278), e32apsk1115(279), e32apsk79(280), e64apsk3245l(281), e64apsk1115(282), e64apsk79(283), e64apsk45(284), e64apsk56(285), e128apsk34(286), e128apsk79(287), e256apsk2945l(288), e256apsk23l(289), e256apsk3145l(290), e256apsk3245(291), e256apsk1115l(292), e256apsk34(293), qpsk1145(294), qpsk415(295), qpsk1445(296), qpsk715(297), qpsk815(298), qpsk3245(299), e8psk715(300), e8psk815(301), e8psk2645(302), e8psk3245(303), e16apsk715(304), e16apsk815(305), e16apsk3245(306), e32apsk23(307) }
    MAX-ACCESS  read-only
    STATUS      current
    DESCRIPTION
        "The most recently seen MODCOD"
    ::= { ntcMultiDemodMonEntry 21 }
    
ntcMultiDemodMonRollOff          OBJECT-TYPE
    SYNTAX      INTEGER { rolloff5(1), rolloff10(2), rolloff15(3), rolloff20(4), rolloff25(5), rolloff35(6), unknown(100) }
    MAX-ACCESS  read-only
    STATUS      current
    DESCRIPTION
        "The receive filter Roll-off factor setting determines the spectrum excess
        bandwidth by controlling the RCRO (Root Cosine Roll-off) factor of the matched
        filter at the demodulator input. The lower the Roll-off factor the higher the
        throughput. Note that increasing the throughput (higher symbolrate) requires
        more power from the satellite or it will result in a lower carrier-to-noise."
    ::= { ntcMultiDemodMonEntry 22 }
    
ntcMultiDemodMonQefM             OBJECT-TYPE
    SYNTAX      Integer32 (-80..140)
    UNITS       "dB"
    MAX-ACCESS  read-only
    STATUS      current
    DESCRIPTION
        "QEF Margin"
    ::= { ntcMultiDemodMonEntry 23 }
    
ntcMultiDemodMonSpectralInv      OBJECT-TYPE
    SYNTAX      INTEGER { direct(0), inverted(1), unknown(2) }
    MAX-ACCESS  read-only
    STATUS      current
    DESCRIPTION
        "Detected spectral inversion"
    ::= { ntcMultiDemodMonEntry 24 }
    
ntcMultiDemodMonVberClp          OBJECT-TYPE
    SYNTAX      INTEGER { exact(0), down(1), up(2), unknown(3) }
    MAX-ACCESS  read-only
    STATUS      current
    DESCRIPTION
        "Value Status."
    ::= { ntcMultiDemodMonEntry 25 }
    
ntcMultiDemodMonBerClp           OBJECT-TYPE
    SYNTAX      INTEGER { exact(0), down(1), up(2), unknown(3) }
    MAX-ACCESS  read-only
    STATUS      current
    DESCRIPTION
        "Value Status."
    ::= { ntcMultiDemodMonEntry 26 }
    
ntcMultiDemodMonQefMClp          OBJECT-TYPE
    SYNTAX      INTEGER { exact(0), down(1), up(2), unknown(3) }
    MAX-ACCESS  read-only
    STATUS      current
    DESCRIPTION
        "Value Status."
    ::= { ntcMultiDemodMonEntry 27 }
    
ntcMultiDemodMonEbNoClp          OBJECT-TYPE
    SYNTAX      INTEGER { exact(0), down(1), up(2), unknown(3) }
    MAX-ACCESS  read-only
    STATUS      current
    DESCRIPTION
        "Value Status."
    ::= { ntcMultiDemodMonEntry 28 }
    
ntcMultiDemodStatsTable          OBJECT-TYPE
    SYNTAX      SEQUENCE OF NtcMultiDemodStatsEntry
    MAX-ACCESS  not-accessible
    STATUS      current
    DESCRIPTION
        "MODCOD statistics table"
    ::= { ntcMultiDemodObjects 6 }

ntcMultiDemodStatsEntry          OBJECT-TYPE
    SYNTAX      NtcMultiDemodStatsEntry
    MAX-ACCESS  not-accessible
    STATUS      current
    DESCRIPTION
        "A conceptual row of the ntcMultiDemodStatsTable."
    INDEX   { ntcMultiDemodStatsInx  }
    ::= { ntcMultiDemodStatsTable 1 }

NtcMultiDemodStatsEntry          ::= SEQUENCE {
    ntcMultiDemodStatsInx               Unsigned32,
    ntcMultiDemodStatsDemodId           INTEGER,
    ntcMultiDemodStatsModCod            INTEGER,
    ntcMultiDemodStatsFrameType         INTEGER,
    ntcMultiDemodStatsPilots            INTEGER,
    ntcMultiDemodStatsFrameCtr          Counter32,
    ntcMultiDemodStatsErrFrameCtr       Counter32,
    ntcMultiDemodStatsCycleSlipCtr      Counter32,
    ntcMultiDemodStatsPacketErrRatio    Integer32,
    ntcMultiDemodStatsLinkMargin        DisplayString,
    ntcMultiDemodStatsCoN               DisplayString,
    ntcMultiDemodStatsCoD               DisplayString,
    ntcMultiDemodStatsCoDpilots         DisplayString,
    ntcMultiDemodStatsCoND              DisplayString,
    ntcMultiDemodStatsCoNDpilots        DisplayString
    }
    
ntcMultiDemodStatsInx            OBJECT-TYPE
    SYNTAX      Unsigned32
    MAX-ACCESS  not-accessible
    STATUS      current
    DESCRIPTION
        "The index of the row"
    ::= { ntcMultiDemodStatsEntry 1 }
    
ntcMultiDemodStatsDemodId        OBJECT-TYPE
    SYNTAX      INTEGER { demod1(1), demod2(2), demod3(3) }
    MAX-ACCESS  read-only
    STATUS      current
    DESCRIPTION
        "The id of the demodulator"
    ::= { ntcMultiDemodStatsEntry 2 }
    
ntcMultiDemodStatsModCod         OBJECT-TYPE
    SYNTAX      INTEGER { qpsk14(1), qpsk13(2), qpsk25(3), qpsk12(4), qpsk35(5), qpsk23(6), qpsk34(7), qpsk45(8), qpsk56(9), qpsk89(10), qpsk910(11), e8psk35(12), e8psk23(13), e8psk34(14), e8psk56(15), e8psk89(16), e8psk910(17), e16apsk23(18), e16apsk34(19), e16apsk45(20), e16apsk56(21), e16apsk89(22), e16apsk910(23), e32apsk34(24), e32apsk45(25), e32apsk56(26), e32apsk89(27), e32apsk910(28), qpsk45180(129), qpsk60180(130), qpsk72180(131), qpsk80180(132), qpsk90180(133), qpsk100180(134), qpsk108180(135), qpsk114180(136), qpsk120180(137), qpsk126180(138), qpsk135180(139), qpsk144180(140), qpsk150180(141), qpsk160180(142), qpsk162180(143), e8psk80180(144), e8psk90180(145), e8psk100180(146), e8psk108180(147), e8psk114180(148), e8psk120180(149), e8psk126180(150), e8psk135180(151), e8psk144180(152), e8psk150180(153), e16apsk80180(154), e16apsk90180(155), e16apsk100180(156), e16apsk108180(157), e16apsk114180(158), e16apsk120180(159), e16apsk126180(160), e16apsk135180(161), e16apsk144180(162), e16apsk150180(163), e16apsk160180(164), e16apsk162180(165), e32apsk100180(166), e32apsk108180(167), e32apsk114180(168), e32apsk120180(169), e32apsk126180(170), e32apsk135180(171), e32apsk144180(172), e32apsk150180(173), e32apsk160180(174), e32apsk162180(175), e64apsk90180(176), e64apsk100180(177), e64apsk108180(178), e64apsk114180(179), e64apsk120180(180), e64apsk126180(181), e64apsk135180(182), e64apsk144180(183), e64apsk150180(184), e64apsk160180(185), e64apsk162180(186), e8pskl80180(187), e8pskl90180(188), e8pskl100180(189), e8pskl108180(190), e8pskl114180(191), e8pskl120180(192), e16apskl80180(193), e16apskl90180(194), e16apskl100180(195), e16apskl108180(196), e16apskl114180(197), e16apskl120180(198), e16apskl126180(199), e16apskl135180(200), e16apskl144180(201), e16apskl150180(202), e16apskl160180(203), e16apskl162180(204), e64apskl90180(205), e64apskl100180(206), e64apskl108180(207), e64apskl114180(208), e64apskl120180(209), e64apskl126180(210), e64apskl135180(211), e64apskl144180(212), e64apskl150180(213), e64apskl160180(214), e64apskl162180(215), qpsk1345(256), qpsk920(257), qpsk1120(258), e8apsk59l(259), e8apsk2645l(260), e8psk2336(261), e8psk2536(262), e8psk1318(263), e16apsk12l(264), e16apsk815l(265), e16apsk59l(266), e16apsk2645(267), e16apsk35(268), e16apsk35l(269), e16apsk2845(270), e16apsk2336(271), e16apsk23l(272), e16apsk2536(273), e16apsk1318(274), e16apsk79(275), e16apsk7790(276), e32apsk23l(277), e32apsk3245(278), e32apsk1115(279), e32apsk79(280), e64apsk3245l(281), e64apsk1115(282), e64apsk79(283), e64apsk45(284), e64apsk56(285), e128apsk34(286), e128apsk79(287), e256apsk2945l(288), e256apsk23l(289), e256apsk3145l(290), e256apsk3245(291), e256apsk1115l(292), e256apsk34(293), qpsk1145(294), qpsk415(295), qpsk1445(296), qpsk715(297), qpsk815(298), qpsk3245(299), e8psk715(300), e8psk815(301), e8psk2645(302), e8psk3245(303), e16apsk715(304), e16apsk815(305), e16apsk3245(306), e32apsk23(307) }
    MAX-ACCESS  read-only
    STATUS      current
    DESCRIPTION
        "Modulation & coding scheme (MODCOD)."
    ::= { ntcMultiDemodStatsEntry 3 }
    
ntcMultiDemodStatsFrameType      OBJECT-TYPE
    SYNTAX      INTEGER { short(0), normal(1) }
    MAX-ACCESS  read-only
    STATUS      current
    DESCRIPTION
        "Dvb-S2 defines 2 FEC-frame types :
        - normal: FECframes of 64800 bits or 8100 bytes
        - short: FECframes of 16200 bits or 2025 bytes Short frames are used when
        working with low symbol rates or with latency sensitive applications."
    ::= { ntcMultiDemodStatsEntry 4 }
    
ntcMultiDemodStatsPilots         OBJECT-TYPE
    SYNTAX      INTEGER { off(0), on(1) }
    MAX-ACCESS  read-only
    STATUS      current
    DESCRIPTION
        "Indicates presence of pilots for the received modcod."
    ::= { ntcMultiDemodStatsEntry 5 }
    
ntcMultiDemodStatsFrameCtr       OBJECT-TYPE
    SYNTAX      Counter32
    UNITS       "frames"
    MAX-ACCESS  read-only
    STATUS      current
    DESCRIPTION
        "Frame counter"
    ::= { ntcMultiDemodStatsEntry 6 }
    
ntcMultiDemodStatsErrFrameCtr    OBJECT-TYPE
    SYNTAX      Counter32
    UNITS       "frames"
    MAX-ACCESS  read-only
    STATUS      current
    DESCRIPTION
        "Errored frame counter"
    ::= { ntcMultiDemodStatsEntry 7 }
    
ntcMultiDemodStatsCycleSlipCtr   OBJECT-TYPE
    SYNTAX      Counter32
    UNITS       "frames"
    MAX-ACCESS  read-only
    STATUS      current
    DESCRIPTION
        "Cycle Slip counter"
    ::= { ntcMultiDemodStatsEntry 8 }
    
ntcMultiDemodStatsPacketErrRatio OBJECT-TYPE
    SYNTAX      Integer32 (0..1000000)
    MAX-ACCESS  read-only
    STATUS      current
    DESCRIPTION
        "Ratio of error frames over total received frames. i.e. Error Frame Count
        divided by Frame Count."
    ::= { ntcMultiDemodStatsEntry 9 }
    
ntcMultiDemodStatsLinkMargin     OBJECT-TYPE
    SYNTAX      DisplayString (SIZE(0..16))
    MAX-ACCESS  read-only
    STATUS      current
    DESCRIPTION
        "link margin"
    ::= { ntcMultiDemodStatsEntry 10 }
    
ntcMultiDemodStatsCoN            OBJECT-TYPE
    SYNTAX      DisplayString (SIZE(0..16))
    MAX-ACCESS  read-only
    STATUS      current
    DESCRIPTION
        "CoN"
    ::= { ntcMultiDemodStatsEntry 11 }
    
ntcMultiDemodStatsCoD            OBJECT-TYPE
    SYNTAX      DisplayString (SIZE(0..16))
    MAX-ACCESS  read-only
    STATUS      current
    DESCRIPTION
        "C/D (carrier to distortion ratio)"
    ::= { ntcMultiDemodStatsEntry 12 }
    
ntcMultiDemodStatsCoDpilots      OBJECT-TYPE
    SYNTAX      DisplayString (SIZE(0..16))
    MAX-ACCESS  read-only
    STATUS      deprecated
    DESCRIPTION
        "C/D on pilots"
    ::= { ntcMultiDemodStatsEntry 13 }
    
ntcMultiDemodStatsCoND           OBJECT-TYPE
    SYNTAX      DisplayString (SIZE(0..16))
    MAX-ACCESS  read-only
    STATUS      current
    DESCRIPTION
        "CoND"
    ::= { ntcMultiDemodStatsEntry 14 }
    
ntcMultiDemodStatsCoNDpilots     OBJECT-TYPE
    SYNTAX      DisplayString (SIZE(0..16))
    MAX-ACCESS  read-only
    STATUS      deprecated
    DESCRIPTION
        "CoND on pilots"
    ::= { ntcMultiDemodStatsEntry 15 }
    
ntcMultiDemodCmCfgInputSelection OBJECT-TYPE
    SYNTAX      INTEGER { lbandRxA(0), lbandRxB(1), ifRx(3) }
    MAX-ACCESS  read-write
    STATUS      current
    DESCRIPTION
        "Toggle the demodulator input between L-BAND Rx A/B or IF Rx"
    DEFVAL { lbandRxA }
    ::= { ntcMultiDemodCmCfg 1 }
    
ntcMultiDemodCmCfgLnbPowerSupply OBJECT-TYPE
    SYNTAX      INTEGER { none(0), e13V0kHz(1), e13V22kHz(2), e18V0kHz(3), e18V22kHz(4) }
    MAX-ACCESS  read-write
    STATUS      current
    DESCRIPTION
        "LNB Power Supply and Tone selection."
    DEFVAL { none }
    ::= { ntcMultiDemodCmCfg 2 }
    
ntcMultiDemodCmMonLbandInputLvl  OBJECT-TYPE
    SYNTAX      Integer32 (-1000..500)
    UNITS       "dBm"
    MAX-ACCESS  read-only
    STATUS      current
    DESCRIPTION
        "Input level measured on the full L-band range. A value of
        -1000 indicates that the measurement is unreliably low."
    ::= { ntcMultiDemodCmMon 1 }
    
ntcMultiDemodEqCliCfgTable       OBJECT-TYPE
    SYNTAX      SEQUENCE OF NtcMultiDemodEqCliCfgEntry
    MAX-ACCESS  not-accessible
    STATUS      current
    DESCRIPTION
        "The Equalink Client configuration table."
    ::= { ntcMultiDemodObjects 9 }

ntcMultiDemodEqCliCfgEntry       OBJECT-TYPE
    SYNTAX      NtcMultiDemodEqCliCfgEntry
    MAX-ACCESS  not-accessible
    STATUS      current
    DESCRIPTION
        "A conceptual row of the ntcMultiDemodEqCliCfgTable."
    AUGMENTS   { ntcMultiDemodCfgEntry }
    ::= { ntcMultiDemodEqCliCfgTable 1 }

NtcMultiDemodEqCliCfgEntry       ::= SEQUENCE {
    ntcMultiDemodEqCfgEnable    NtcEnable
    }
    
ntcMultiDemodEqCfgEnable         OBJECT-TYPE
    SYNTAX      NtcEnable
    MAX-ACCESS  read-write
    STATUS      current
    DESCRIPTION
        "Enable or disable the demodulator function"
    DEFVAL { off }
    ::= { ntcMultiDemodEqCliCfgEntry 1 }
    
ntcMultiDemodBuCarCfgTable       OBJECT-TYPE
    SYNTAX      SEQUENCE OF NtcMultiDemodBuCarCfgEntry
    MAX-ACCESS  not-accessible
    STATUS      current
    DESCRIPTION
        "Backup Carrier Configuration table"
    ::= { ntcMultiDemodObjects 10 }

ntcMultiDemodBuCarCfgEntry       OBJECT-TYPE
    SYNTAX      NtcMultiDemodBuCarCfgEntry
    MAX-ACCESS  not-accessible
    STATUS      current
    DESCRIPTION
        "A conceptual row of the ntcMultiDemodBuCarCfgTable."
    AUGMENTS   { ntcMultiDemodCfgEntry }
    ::= { ntcMultiDemodBuCarCfgTable 1 }

NtcMultiDemodBuCarCfgEntry       ::= SEQUENCE {
    ntcMultiDemodBuCarCfgEnable        NtcEnable,
    ntcMultiDemodBuCarCfgInpFreq       Unsigned32,
    ntcMultiDemodBuCarCfgSymbolRate    Unsigned32,
    ntcMultiDemodBuCarCfgSwitchTmo     Unsigned32,
    ntcMultiDemodBuCarCfgRfFreq        DisplayString
    }
    
ntcMultiDemodBuCarCfgEnable      OBJECT-TYPE
    SYNTAX      NtcEnable
    MAX-ACCESS  read-write
    STATUS      current
    DESCRIPTION
        "Enable or disable carrier switching between the main demodulator carrier and
        the backup demodulator carrier."
    DEFVAL { off }
    ::= { ntcMultiDemodBuCarCfgEntry 1 }
    
ntcMultiDemodBuCarCfgInpFreq     OBJECT-TYPE
    SYNTAX      Unsigned32
    UNITS       "Hz"
    MAX-ACCESS  read-write
    STATUS      current
    DESCRIPTION
        "Backup carrier input frequency setting."
    DEFVAL { 2000000000 }
    ::= { ntcMultiDemodBuCarCfgEntry 2 }
    
ntcMultiDemodBuCarCfgSymbolRate  OBJECT-TYPE
    SYNTAX      Unsigned32
    UNITS       "baud"
    MAX-ACCESS  read-write
    STATUS      current
    DESCRIPTION
        "Symbol rate of the backup carrier"
    DEFVAL { 10000000 }
    ::= { ntcMultiDemodBuCarCfgEntry 3 }
    
ntcMultiDemodBuCarCfgSwitchTmo   OBJECT-TYPE
    SYNTAX      Unsigned32
    UNITS       "sec"
    MAX-ACCESS  read-write
    STATUS      current
    DESCRIPTION
        "This switch timeout defines the period in seconds, after configuring the
        active carrier or after switching between the main and backup carrier, when
        carrier switching is disabled."
    DEFVAL { 60 }
    ::= { ntcMultiDemodBuCarCfgEntry 4 }
    
ntcMultiDemodBuCarCfgRfFreq      OBJECT-TYPE
    SYNTAX      DisplayString (SIZE(0..20))
    UNITS       "Hz"
    MAX-ACCESS  read-write
    STATUS      current
    DESCRIPTION
        "Backup carrier RF frequency"
    DEFVAL { "0" }
    ::= { ntcMultiDemodBuCarCfgEntry 5 }
    
ntcMultiDemodBuCarMonTable       OBJECT-TYPE
    SYNTAX      SEQUENCE OF NtcMultiDemodBuCarMonEntry
    MAX-ACCESS  not-accessible
    STATUS      current
    DESCRIPTION
        "Backup Carrier Monitoring Table"
    ::= { ntcMultiDemodObjects 11 }

ntcMultiDemodBuCarMonEntry       OBJECT-TYPE
    SYNTAX      NtcMultiDemodBuCarMonEntry
    MAX-ACCESS  not-accessible
    STATUS      current
    DESCRIPTION
        "A conceptual row of the ntcMultiDemodBuCarMonTable."
    INDEX   { ntcMultiDemodBuCarMonDemodId  }
    ::= { ntcMultiDemodBuCarMonTable 1 }

NtcMultiDemodBuCarMonEntry       ::= SEQUENCE {
    ntcMultiDemodBuCarMonDemodId      INTEGER,
    ntcMultiDemodBuCarMonActiveCar    INTEGER,
    ntcMultiDemodBuCarMonSwitchCnt    Counter32
    }
    
ntcMultiDemodBuCarMonDemodId     OBJECT-TYPE
    SYNTAX      INTEGER { demod1(1), demod2(2), demod3(3) }
    MAX-ACCESS  not-accessible
    STATUS      current
    DESCRIPTION
        "The id of the demodulator"
    ::= { ntcMultiDemodBuCarMonEntry 1 }
    
ntcMultiDemodBuCarMonActiveCar   OBJECT-TYPE
    SYNTAX      INTEGER { main(0), backup(1) }
    MAX-ACCESS  read-only
    STATUS      current
    DESCRIPTION
        "Displays if either the main or the backup carrier is active."
    ::= { ntcMultiDemodBuCarMonEntry 2 }
    
ntcMultiDemodBuCarMonSwitchCnt   OBJECT-TYPE
    SYNTAX      Counter32
    MAX-ACCESS  read-only
    STATUS      current
    DESCRIPTION
        "Counts the number of times the device switched between the main and backup
        demodulator carrier."
    ::= { ntcMultiDemodBuCarMonEntry 3 }
    
ntcMultiDemodNlpdCliCfgTable     OBJECT-TYPE
    SYNTAX      SEQUENCE OF NtcMultiDemodNlpdCliCfgEntry
    MAX-ACCESS  not-accessible
    STATUS      current
    DESCRIPTION
        "Non-Linear Post Compensation Configuration table"
    ::= { ntcMultiDemodObjects 12 }

ntcMultiDemodNlpdCliCfgEntry     OBJECT-TYPE
    SYNTAX      NtcMultiDemodNlpdCliCfgEntry
    MAX-ACCESS  not-accessible
    STATUS      current
    DESCRIPTION
        "A conceptual row of the ntcMultiDemodNlpdCliCfgTable."
    AUGMENTS   { ntcMultiDemodCfgEntry }
    ::= { ntcMultiDemodNlpdCliCfgTable 1 }

NtcMultiDemodNlpdCliCfgEntry     ::= SEQUENCE {
    ntcMultiDemodNldCfgEnable       NtcEnable,
    ntcMultiDemodNldCfgTrCenFreq    DisplayString,
    ntcMultiDemodNldCfgTrBandw      Unsigned32
    }
    
ntcMultiDemodNldCfgEnable        OBJECT-TYPE
    SYNTAX      NtcEnable
    MAX-ACCESS  read-write
    STATUS      current
    DESCRIPTION
        "Enable or disable the demodulator function"
    DEFVAL { off }
    ::= { ntcMultiDemodNlpdCliCfgEntry 1 }
    
ntcMultiDemodNldCfgTrCenFreq     OBJECT-TYPE
    SYNTAX      DisplayString (SIZE(0..20))
    UNITS       "Hz"
    MAX-ACCESS  read-write
    STATUS      current
    DESCRIPTION
        "Transponder Center RF frequency setting."
    DEFVAL { "15000000000" }
    ::= { ntcMultiDemodNlpdCliCfgEntry 2 }
    
ntcMultiDemodNldCfgTrBandw       OBJECT-TYPE
    SYNTAX      Unsigned32 (10000000..80000000)
    UNITS       "Hz"
    MAX-ACCESS  read-write
    STATUS      current
    DESCRIPTION
        "Transponder Bandwidth expressed im Mhz."
    DEFVAL { 36000000 }
    ::= { ntcMultiDemodNlpdCliCfgEntry 3 }
    
ntcMultiDemodExtConvTable        OBJECT-TYPE
    SYNTAX      SEQUENCE OF NtcMultiDemodExtConvEntry
    MAX-ACCESS  not-accessible
    STATUS      current
    DESCRIPTION
        "External Converter Configuration table"
    ::= { ntcMultiDemodObjects 13 }

ntcMultiDemodExtConvEntry        OBJECT-TYPE
    SYNTAX      NtcMultiDemodExtConvEntry
    MAX-ACCESS  not-accessible
    STATUS      current
    DESCRIPTION
        "A conceptual row of the ntcMultiDemodExtConvTable."
    AUGMENTS   { ntcMultiDemodCfgEntry }
    ::= { ntcMultiDemodExtConvTable 1 }

NtcMultiDemodExtConvEntry        ::= SEQUENCE {
    ntcMultiDemodExtConvEnable         NtcEnable,
    ntcMultiDemodExtConvLoFrequency    DisplayString,
    ntcMultiDemodExtConvSpectralInv    INTEGER
    }
    
ntcMultiDemodExtConvEnable       OBJECT-TYPE
    SYNTAX      NtcEnable
    MAX-ACCESS  read-write
    STATUS      current
    DESCRIPTION
        "Enable or disable the demodulator function"
    DEFVAL { off }
    ::= { ntcMultiDemodExtConvEntry 1 }
    
ntcMultiDemodExtConvLoFrequency  OBJECT-TYPE
    SYNTAX      DisplayString (SIZE(0..20))
    UNITS       "Hz"
    MAX-ACCESS  read-write
    STATUS      current
    DESCRIPTION
        "LO frequency"
    DEFVAL { "0" }
    ::= { ntcMultiDemodExtConvEntry 2 }
    
ntcMultiDemodExtConvSpectralInv  OBJECT-TYPE
    SYNTAX      INTEGER { direct(1), inverted(2) }
    MAX-ACCESS  read-write
    STATUS      current
    DESCRIPTION
        "Specifies in the external LO converter inverts the spectrum or not."
    DEFVAL { direct }
    ::= { ntcMultiDemodExtConvEntry 3 }
    
ntcMultiDemodCmConvEnable        OBJECT-TYPE
    SYNTAX      NtcEnable
    MAX-ACCESS  read-write
    STATUS      current
    DESCRIPTION
        "Enable or disable the demodulator function"
    DEFVAL { off }
    ::= { ntcMultiDemodCmConv 1 }
    
ntcMultiDemodCmConvLoFrequency   OBJECT-TYPE
    SYNTAX      DisplayString (SIZE(0..20))
    UNITS       "Hz"
    MAX-ACCESS  read-write
    STATUS      current
    DESCRIPTION
        "LO frequency"
    DEFVAL { "0" }
    ::= { ntcMultiDemodCmConv 2 }
    
ntcMultiDemodCmConvSpectralInv   OBJECT-TYPE
    SYNTAX      INTEGER { direct(1), inverted(2) }
    MAX-ACCESS  read-write
    STATUS      current
    DESCRIPTION
        "Specifies in the external LO converter inverts the spectrum or not."
    DEFVAL { direct }
    ::= { ntcMultiDemodCmConv 3 }
    

--
--  Module Conformance
--

ntcMultiDemodConfGrpV1Standard   OBJECT-GROUP
    OBJECTS    {
                   ntcMultiDemodAlmGeneralDemod,
                   ntcMultiDemodAlmInternalError,
                   ntcMultiDemodAlmInputSaturated,
                   ntcMultiDemodAlmNoLock,
                   ntcMultiDemodAlmLnbPowerControl,
                   ntcMultiDemodAlmDecoderOvrload,
                   ntcMultiDemodAlmNoPlLock,
                   ntcMultiDemodAlmBufferOverflow,
                   ntcMultiDemodASGeneralDemod,
                   ntcMultiDemodASInternalError,
                   ntcMultiDemodASInputSaturated,
                   ntcMultiDemodASNoPlLock,
                   ntcMultiDemodASNoLock,
                   ntcMultiDemodASLnbPowerControl,
                   ntcMultiDemodASDecoderOverloaded,
                   ntcMultiDemodCfgEnable,
                   ntcMultiDemodCfgMode,
                   ntcMultiDemodCfgInputFrequency,
                   ntcMultiDemodCfgSymbolRate,
                   ntcMultiDemodCfgRollOff,
                   ntcMultiDemodCfgInputSelection,
                   ntcMultiDemodCfgSpectralInv,
                   ntcMultiDemodCfgPlScrambSig,
                   ntcMultiDemodCfgLnbPowerSupply,
                   ntcMultiDemodCfgHardwareId,
                   ntcMultiDemodCfgModCodDvbs,
                   ntcMultiDemodCfgStreamMode,
                   ntcMultiDemodCfgInterfaceRate,
                   ntcMultiDemodCfgAcqRange,
                   ntcMultiDemodCfgPlhdrScramSeq,
                   ntcMultiDemodCfgRfFrequency,
                   ntcMultiDemodCfgModCodAmcDl,
                   ntcExtMultiDemodCfgOpMode,
                   ntcMultiDemodMonLbandInputLvl,
                   ntcMultiDemodMonCarrierInputLvl,
                   ntcMultiDemodMonEsNo,
                   ntcMultiDemodMonPhaseNoiseIndic,
                   ntcMultiDemodMonOffRefMask,
                   ntcMultiDemodMonNonLinIndic,
                   ntcMultiDemodMonSymbolRate,
                   ntcMultiDemodMonCarrierOffset,
                   ntcMultiDemodMonFrameCounter,
                   ntcMultiDemodMonDummyFrameCtr,
                   ntcMultiDemodMonErroredFrameCtr,
                   ntcMultiDemodMonCycleSlipCtr,
                   ntcMultiDemodMonLastModCod,
                   ntcMultiDemodModCodStatsReset,
                   ntcMultiDemodMonVber,
                   ntcMultiDemodMonBer,
                   ntcMultiDemodMonEbNo,
                   ntcMultiDemodMonLinkMargin,
                   ntcMultiDemodMonOperationalState,
                   ntcMultiDemodMonLastNonDumModCod,
                   ntcMultiDemodMonRollOff,
                   ntcMultiDemodMonQefM,
                   ntcMultiDemodMonSpectralInv,
                   ntcMultiDemodMonVberClp,
                   ntcMultiDemodMonBerClp,
                   ntcMultiDemodMonQefMClp,
                   ntcMultiDemodMonEbNoClp,
                   ntcMultiDemodStatsDemodId,
                   ntcMultiDemodStatsModCod,
                   ntcMultiDemodStatsFrameType,
                   ntcMultiDemodStatsPilots,
                   ntcMultiDemodStatsFrameCtr,
                   ntcMultiDemodStatsErrFrameCtr,
                   ntcMultiDemodStatsCycleSlipCtr,
                   ntcMultiDemodStatsPacketErrRatio,
                   ntcMultiDemodStatsLinkMargin,
                   ntcMultiDemodStatsCoN,
                   ntcMultiDemodStatsCoD,
                   ntcMultiDemodStatsCoND,
                   ntcMultiDemodCmCfgInputSelection,
                   ntcMultiDemodCmCfgLnbPowerSupply,
                   ntcMultiDemodCmMonLbandInputLvl,
                   ntcMultiDemodEqCfgEnable,
                   ntcMultiDemodBuCarCfgEnable,
                   ntcMultiDemodBuCarCfgInpFreq,
                   ntcMultiDemodBuCarCfgSymbolRate,
                   ntcMultiDemodBuCarCfgSwitchTmo,
                   ntcMultiDemodBuCarCfgRfFreq,
                   ntcMultiDemodBuCarMonActiveCar,
                   ntcMultiDemodBuCarMonSwitchCnt,
                   ntcMultiDemodNldCfgEnable,
                   ntcMultiDemodNldCfgTrCenFreq,
                   ntcMultiDemodNldCfgTrBandw,
                   ntcMultiDemodExtConvEnable,
                   ntcMultiDemodExtConvLoFrequency,
                   ntcMultiDemodExtConvSpectralInv,
                   ntcMultiDemodCmConvEnable,
                   ntcMultiDemodCmConvLoFrequency,
                   ntcMultiDemodCmConvSpectralInv
               }
    STATUS      current
    DESCRIPTION
        "Managed objects that constitute version 1 of a system device with standard capabilities."
    ::= { ntcMultiDemodConfGroup 1}
    
ntcMultiDemodConfGrpObsolete     OBJECT-GROUP
    OBJECTS    {
                   ntcMultiDemodStatsCoDpilots,
                   ntcMultiDemodStatsCoNDpilots
               }
    STATUS      obsolete
    DESCRIPTION
        "Managed objects which are deprecated or obsolete"
    ::= { ntcMultiDemodConfGroup 2}
    
ntcMultiDemodConfCompV1Standard  MODULE-COMPLIANCE
    STATUS      current
    DESCRIPTION
        "Compliance statement for Newtec device MIB implementations."
    MODULE  -- this module
    MANDATORY-GROUPS
                  {
                      ntcMultiDemodConfGrpV1Standard
                  }
    ::= { ntcMultiDemodConfCompliance  1 }
    

END
