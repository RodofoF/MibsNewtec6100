NEWTEC-TRAFFICSHAPER-MIB DEFINITIONS ::= BEGIN

IMPORTS
    Unsigned32,
    Counter64,
    MODULE-IDENTITY,
    OBJECT-IDENTITY,
    OBJECT-TYPE
        FROM SNMPv2-SMI

    MODULE-COMPLIANCE,
    OBJECT-GROUP
        FROM SNMPv2-CONF
    
    NtcEnable,
    NtcNetworkAddress
        FROM NEWTEC-TC-MIB

    DisplayString,
    RowStatus
        FROM SNMPv2-TC

    ntcFunction
        FROM NEWTEC-MAIN-MIB;


--
--  Module Identification
--

ntcTrafficShaper   MODULE-IDENTITY
    LAST-UPDATED "201409090900Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular Traffic Shaper MIB containing definitions for Traffic Shaper
        functionality."

    REVISION  "201409090900Z"
    DESCRIPTION
        "Minimum value of string keys adjusted"
    REVISION  "201409041200Z"
    DESCRIPTION
        "ntcTrfMaxQTime and ntcTrfMaxQTExtime units corrected"
    REVISION  "201407150800Z"
    DESCRIPTION
        "read-write becomes read-create"
    REVISION  "201402031200Z"
    DESCRIPTION
        "Added support for symbolrate-based shaping"
    REVISION  "201307050600Z"
    DESCRIPTION
        "Some defaults changed"
    REVISION  "201305220600Z"
    DESCRIPTION
        "Release for MDM6000 R1.1"
    REVISION  "201301081200Z"
    DESCRIPTION
        "Release for NOP1760 R1.0"
    REVISION  "201206281200Z"
    DESCRIPTION
        "Release for M6100 R1.2"
    ::= { ntcFunction  2000 }
    

--
-- Top-Level Structure
--

-- ntcTrafficShaper content

ntcTrfShapeObjects               OBJECT-IDENTITY
    STATUS        current
    DESCRIPTION   "Container holding ntcTrfShapeObjects definitions."
    ::= { ntcTrafficShaper 1 }
    
ntcTrfShapeConformance           OBJECT-IDENTITY
    STATUS        current
    DESCRIPTION   "Conformance requirements."
    ::= { ntcTrafficShaper 2 }
    
-- ntcTrfShapeObjects content

ntcTrfShMonitor                  OBJECT-IDENTITY
    STATUS        current
    DESCRIPTION   "Container holding ntcTrfShMonitor definitions."
    ::= { ntcTrfShapeObjects 5 }
    
-- ntcTrfShapeConformance content

ntcTrfShapeConfCompliance        OBJECT-IDENTITY
    STATUS        current
    DESCRIPTION   "Device compliance statements."
    ::= { ntcTrfShapeConformance 1 }
    
ntcTrfShapeConfGroup             OBJECT-IDENTITY
    STATUS        current
    DESCRIPTION   "Groups used by device compliance statements."
    ::= { ntcTrfShapeConformance 2 }
    

--
-- Managed Objects
--

ntcTrfShEnable                   OBJECT-TYPE
    SYNTAX      NtcEnable
    MAX-ACCESS  read-write
    STATUS      current
    DESCRIPTION
        "Enable or disable the Traffic Shaping functionality."
    DEFVAL { off }
    ::= { ntcTrfShapeObjects 1 }
    
ntcTrfShInputSelection           OBJECT-TYPE
    SYNTAX      INTEGER { none(0), data1(1), data2(2), data(3) }
    MAX-ACCESS  read-write
    STATUS      current
    DESCRIPTION
        "Configures the input interface for the traffic shaper."
    DEFVAL { data1 }
    ::= { ntcTrfShapeObjects 2 }
    
ntcTrfShClassificationTable      OBJECT-TYPE
    SYNTAX      SEQUENCE OF NtcTrfShClassificationEntry
    MAX-ACCESS  not-accessible
    STATUS      current
    DESCRIPTION
        "A table containing the ntcTrfShClassification"
    ::= { ntcTrfShapeObjects 3 }

ntcTrfShClassificationEntry      OBJECT-TYPE
    SYNTAX      NtcTrfShClassificationEntry
    MAX-ACCESS  not-accessible
    STATUS      current
    DESCRIPTION
        "A conceptual row of the ntcTrfShClassificationTable."
    INDEX   { ntcTrfShClassificationInx  }
    ::= { ntcTrfShClassificationTable 1 }

NtcTrfShClassificationEntry      ::= SEQUENCE {
    ntcTrfShClassificationInx       Unsigned32,
    ntcTrfShapeClassifName          DisplayString,
    ntcTrfShClassificationEnable    NtcEnable,
    ntcTrfShapeUseNetwAddress       INTEGER,
    ntcTrfShapeNetwAddress          NtcNetworkAddress,
    ntcTrfShapeExpr                 DisplayString,
    ntcTrfShapeShapingNode          DisplayString
    }
    
ntcTrfShClassificationInx        OBJECT-TYPE
    SYNTAX      Unsigned32
    MAX-ACCESS  not-accessible
    STATUS      current
    DESCRIPTION
        "The index of the traffic classification table."
    ::= { ntcTrfShClassificationEntry 1 }
    
ntcTrfShapeClassifName           OBJECT-TYPE
    SYNTAX      DisplayString (SIZE(0..30))
    MAX-ACCESS  read-write
    STATUS      current
    DESCRIPTION
        "The name of the traffic classification rule"
    DEFVAL { "" }
    ::= { ntcTrfShClassificationEntry 2 }
    
ntcTrfShClassificationEnable     OBJECT-TYPE
    SYNTAX      NtcEnable
    MAX-ACCESS  read-write
    STATUS      current
    DESCRIPTION
        "Enable or disable the corresponding classification rule."
    DEFVAL { off }
    ::= { ntcTrfShClassificationEntry 3 }
    
ntcTrfShapeUseNetwAddress        OBJECT-TYPE
    SYNTAX      INTEGER { no(0), yes(1) }
    MAX-ACCESS  read-write
    STATUS      current
    DESCRIPTION
        "Use the specified network address as a classification criterion. If a full
        classification expression is also specified, it is AND-ed with this network
        address criterion."
    DEFVAL { no }
    ::= { ntcTrfShClassificationEntry 4 }
    
ntcTrfShapeNetwAddress           OBJECT-TYPE
    SYNTAX      NtcNetworkAddress
    MAX-ACCESS  read-write
    STATUS      current
    DESCRIPTION
        "IP address and prefix to be used as a classification criterion. Only used when
        UseNetworkAddress is true."
    DEFVAL { "0.0.0.0/24" }
    ::= { ntcTrfShClassificationEntry 5 }
    
ntcTrfShapeExpr                  OBJECT-TYPE
    SYNTAX      DisplayString (SIZE(0..1000))
    MAX-ACCESS  read-write
    STATUS      current
    DESCRIPTION
        "The classification expression to be matched against incoming traffic."
    DEFVAL { "" }
    ::= { ntcTrfShClassificationEntry 6 }
    
ntcTrfShapeShapingNode           OBJECT-TYPE
    SYNTAX      DisplayString (SIZE(0..30))
    MAX-ACCESS  read-write
    STATUS      current
    DESCRIPTION
        "The name of the traffic shaping node."
    DEFVAL { "" }
    ::= { ntcTrfShClassificationEntry 7 }
    
ntcTrfShShapingNodeTable         OBJECT-TYPE
    SYNTAX      SEQUENCE OF NtcTrfShShapingNodeEntry
    MAX-ACCESS  not-accessible
    STATUS      current
    DESCRIPTION
        "A table containing the ntcTrfShShapingNode"
    ::= { ntcTrfShapeObjects 4 }

ntcTrfShShapingNodeEntry         OBJECT-TYPE
    SYNTAX      NtcTrfShShapingNodeEntry
    MAX-ACCESS  not-accessible
    STATUS      current
    DESCRIPTION
        "A conceptual row of the ntcTrfShShapingNodeTable."
    INDEX   { ntcTrfShShapingNodeInx  }
    ::= { ntcTrfShShapingNodeTable 1 }

NtcTrfShShapingNodeEntry         ::= SEQUENCE {
    ntcTrfShShapingNodeInx       Unsigned32,
    ntcTrfShapeNodeName          DisplayString,
    ntcTrfShShapingNodeEnable    NtcEnable,
    ntcTrfShapeParentName        DisplayString,
    ntcTrfShapeCir               Unsigned32,
    ntcTrfShapePir               Unsigned32,
    ntcTrfShapeDestChannel       DisplayString,
    ntcTrfShapePrio              Unsigned32,
    ntcTrfMaxQTime               Unsigned32
    }
    
ntcTrfShShapingNodeInx           OBJECT-TYPE
    SYNTAX      Unsigned32
    MAX-ACCESS  not-accessible
    STATUS      current
    DESCRIPTION
        "The index of the traffic shaping node table."
    ::= { ntcTrfShShapingNodeEntry 1 }
    
ntcTrfShapeNodeName              OBJECT-TYPE
    SYNTAX      DisplayString (SIZE(0..30))
    MAX-ACCESS  read-write
    STATUS      current
    DESCRIPTION
        "The name of the traffic shaping node."
    DEFVAL { "" }
    ::= { ntcTrfShShapingNodeEntry 2 }
    
ntcTrfShShapingNodeEnable        OBJECT-TYPE
    SYNTAX      NtcEnable
    MAX-ACCESS  read-write
    STATUS      current
    DESCRIPTION
        "Enable or disable the corresponding shaping node."
    DEFVAL { off }
    ::= { ntcTrfShShapingNodeEntry 3 }
    
ntcTrfShapeParentName            OBJECT-TYPE
    SYNTAX      DisplayString (SIZE(0..30))
    MAX-ACCESS  read-write
    STATUS      current
    DESCRIPTION
        "The name of the parent node of this traffic shaping node."
    DEFVAL { "Root" }
    ::= { ntcTrfShShapingNodeEntry 4 }
    
ntcTrfShapeCir                   OBJECT-TYPE
    SYNTAX      Unsigned32
    MAX-ACCESS  read-write
    STATUS      current
    DESCRIPTION
        "Define the guaranteed information rate (CIR) for this shaping node."
    DEFVAL { 0 }
    ::= { ntcTrfShShapingNodeEntry 5 }
    
ntcTrfShapePir                   OBJECT-TYPE
    SYNTAX      Unsigned32
    MAX-ACCESS  read-write
    STATUS      current
    DESCRIPTION
        "Define the peak information rate (PIR) for this shaping node."
    DEFVAL { 10000000 }
    ::= { ntcTrfShShapingNodeEntry 6 }
    
ntcTrfShapeDestChannel           OBJECT-TYPE
    SYNTAX      DisplayString (SIZE(0..100))
    MAX-ACCESS  read-write
    STATUS      current
    DESCRIPTION
        "The name of the destination channel for this shaping rule. This is defined in
        another functional block. (e.g. MPE, GSE, ...)"
    DEFVAL { "" }
    ::= { ntcTrfShShapingNodeEntry 7 }
    
ntcTrfShapePrio                  OBJECT-TYPE
    SYNTAX      Unsigned32
    MAX-ACCESS  read-write
    STATUS      current
    DESCRIPTION
        "Define the priority for this shaping node when dividing rate between nodes."
    DEFVAL { 50 }
    ::= { ntcTrfShShapingNodeEntry 8 }
    
ntcTrfMaxQTime                   OBJECT-TYPE
    SYNTAX      Unsigned32
    UNITS       "ms"
    MAX-ACCESS  read-write
    STATUS      current
    DESCRIPTION
        "The maximum time packets are allowed to remain in a shaping queue before being
        dropped."
    DEFVAL { 100 }
    ::= { ntcTrfShShapingNodeEntry 9 }
    
ntcTrfShMonFwdBytes              OBJECT-TYPE
    SYNTAX      Counter64
    UNITS       "bytes"
    MAX-ACCESS  read-only
    STATUS      current
    DESCRIPTION
        "Number of forwarded bytes."
    ::= { ntcTrfShMonitor 1 }
    
ntcTrfShMonFwdPackets            OBJECT-TYPE
    SYNTAX      Counter64
    UNITS       "packets"
    MAX-ACCESS  read-only
    STATUS      current
    DESCRIPTION
        "Number of forwarded packets."
    ::= { ntcTrfShMonitor 2 }
    
ntcTrfShMonDropBytes             OBJECT-TYPE
    SYNTAX      Counter64
    UNITS       "bytes"
    MAX-ACCESS  read-only
    STATUS      current
    DESCRIPTION
        "Number of dropped bytes."
    ::= { ntcTrfShMonitor 3 }
    
ntcTrfShMonDropPackets           OBJECT-TYPE
    SYNTAX      Counter64
    UNITS       "packets"
    MAX-ACCESS  read-only
    STATUS      current
    DESCRIPTION
        "Number of dropped packets."
    ::= { ntcTrfShMonitor 4 }
    
ntcTrfShMonShapingNodeTable      OBJECT-TYPE
    SYNTAX      SEQUENCE OF NtcTrfShMonShapingNodeEntry
    MAX-ACCESS  not-accessible
    STATUS      current
    DESCRIPTION
        "Traffic Shaping Monitoring"
    ::= { ntcTrfShMonitor 5 }

ntcTrfShMonShapingNodeEntry      OBJECT-TYPE
    SYNTAX      NtcTrfShMonShapingNodeEntry
    MAX-ACCESS  not-accessible
    STATUS      current
    DESCRIPTION
        "A conceptual row of the ntcTrfShMonShapingNodeTable."
    INDEX   { ntcTrfShMonShapingNodeInx  }
    ::= { ntcTrfShMonShapingNodeTable 1 }

NtcTrfShMonShapingNodeEntry      ::= SEQUENCE {
    ntcTrfShMonShapingNodeInx      Unsigned32,
    ntcTrfMonShNodeName            DisplayString,
    ntcTrfMonShNodeFwdByte         Counter64,
    ntcTfrMonShNodeFwdPackets      Counter64,
    ntcTrfMonShNodeDropByt         Counter64,
    ntcTrfShapeNodeDropPackets     Counter64,
    ntcTrfShapeNodeAverageDelay    Unsigned32,
    ntcTrfShapeNodeVolRate         Counter64,
    ntcTrfShapeNodeDropRate        Counter64,
    ntcTrfShapeNodeVolUnit         INTEGER
    }
    
ntcTrfShMonShapingNodeInx        OBJECT-TYPE
    SYNTAX      Unsigned32
    MAX-ACCESS  not-accessible
    STATUS      current
    DESCRIPTION
        "Index of the Shaping Node Counter table."
    ::= { ntcTrfShMonShapingNodeEntry 1 }
    
ntcTrfMonShNodeName              OBJECT-TYPE
    SYNTAX      DisplayString (SIZE(0..30))
    MAX-ACCESS  read-only
    STATUS      current
    DESCRIPTION
        "The name of the traffic shaping node."
    ::= { ntcTrfShMonShapingNodeEntry 2 }
    
ntcTrfMonShNodeFwdByte           OBJECT-TYPE
    SYNTAX      Counter64
    MAX-ACCESS  read-only
    STATUS      current
    DESCRIPTION
        "Forwarded Volume."
    ::= { ntcTrfShMonShapingNodeEntry 3 }
    
ntcTfrMonShNodeFwdPackets        OBJECT-TYPE
    SYNTAX      Counter64
    UNITS       "packets"
    MAX-ACCESS  read-only
    STATUS      current
    DESCRIPTION
        "Number of forwarded packets."
    ::= { ntcTrfShMonShapingNodeEntry 4 }
    
ntcTrfMonShNodeDropByt           OBJECT-TYPE
    SYNTAX      Counter64
    UNITS       "bytes"
    MAX-ACCESS  read-only
    STATUS      current
    DESCRIPTION
        "Number of dropped bytes."
    ::= { ntcTrfShMonShapingNodeEntry 5 }
    
ntcTrfShapeNodeDropPackets       OBJECT-TYPE
    SYNTAX      Counter64
    UNITS       "packets"
    MAX-ACCESS  read-only
    STATUS      current
    DESCRIPTION
        "Number of dropped packets."
    ::= { ntcTrfShMonShapingNodeEntry 6 }
    
ntcTrfShapeNodeAverageDelay      OBJECT-TYPE
    SYNTAX      Unsigned32
    UNITS       "ms"
    MAX-ACCESS  read-only
    STATUS      current
    DESCRIPTION
        "Average traffic delay"
    ::= { ntcTrfShMonShapingNodeEntry 7 }
    
ntcTrfShapeNodeVolRate           OBJECT-TYPE
    SYNTAX      Counter64
    MAX-ACCESS  read-only
    STATUS      current
    DESCRIPTION
        "Encapsulated data output rate in volume units."
    ::= { ntcTrfShMonShapingNodeEntry 8 }
    
ntcTrfShapeNodeDropRate          OBJECT-TYPE
    SYNTAX      Counter64
    UNITS       "bps"
    MAX-ACCESS  read-only
    STATUS      current
    DESCRIPTION
        "Drop bit rate in bps."
    ::= { ntcTrfShMonShapingNodeEntry 9 }
    
ntcTrfShapeNodeVolUnit           OBJECT-TYPE
    SYNTAX      INTEGER { bytes(0), symbols(1) }
    MAX-ACCESS  read-only
    STATUS      current
    DESCRIPTION
        "Volume Unit."
    ::= { ntcTrfShMonShapingNodeEntry 10 }
    
ntcTrfShMonReset                 OBJECT-TYPE
    SYNTAX      INTEGER { counting(0), reset(1) }
    MAX-ACCESS  read-write
    STATUS      current
    DESCRIPTION
        "Reset the Traffic Shaping counters."
    DEFVAL { counting }
    ::= { ntcTrfShMonitor 6 }
    
ntcTrfShMonFwdBitRate            OBJECT-TYPE
    SYNTAX      Counter64
    UNITS       "bps"
    MAX-ACCESS  read-only
    STATUS      current
    DESCRIPTION
        "Encapsulated data output bit rate in bps."
    ::= { ntcTrfShMonitor 7 }
    
ntcTrfShExtClassifTable          OBJECT-TYPE
    SYNTAX      SEQUENCE OF NtcTrfShExtClassifEntry
    MAX-ACCESS  not-accessible
    STATUS      current
    DESCRIPTION
        "A table containing the ntcTrfShExtClassif"
    ::= { ntcTrfShapeObjects 6 }

ntcTrfShExtClassifEntry          OBJECT-TYPE
    SYNTAX      NtcTrfShExtClassifEntry
    MAX-ACCESS  not-accessible
    STATUS      current
    DESCRIPTION
        "A conceptual row of the ntcTrfShExtClassifTable."
    INDEX   { ntcTrfShExtClassifName  }
    ::= { ntcTrfShExtClassifTable 1 }

NtcTrfShExtClassifEntry          ::= SEQUENCE {
    ntcTrfShExtClassifName         DisplayString,
    ntcTrfShExtClassifRowStatus    RowStatus,
    ntcTrfShExtClassifEnable       NtcEnable,
    ntcTrfShapeExtUseNetwAddr      INTEGER,
    ntcTrfShapeExtNetwAddr         NtcNetworkAddress,
    ntcTrfShapeExtExpr             DisplayString,
    ntcTrfShapeExtShapingNode      DisplayString,
    ntcTrfShapeExtMatchingOrder    Unsigned32
    }
    
ntcTrfShExtClassifName           OBJECT-TYPE
    SYNTAX      DisplayString (SIZE(1..30))
    MAX-ACCESS  not-accessible
    STATUS      current
    DESCRIPTION
        "The name of the traffic classification rule"
    ::= { ntcTrfShExtClassifEntry 1 }
    
ntcTrfShExtClassifRowStatus      OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcTrfShExtClassifEntry 2 }
    
ntcTrfShExtClassifEnable         OBJECT-TYPE
    SYNTAX      NtcEnable
    MAX-ACCESS  read-create
    STATUS      current
    DESCRIPTION
        "Enable or disable the corresponding classification rule."
    ::= { ntcTrfShExtClassifEntry 3 }
    
ntcTrfShapeExtUseNetwAddr        OBJECT-TYPE
    SYNTAX      INTEGER { no(0), yes(1) }
    MAX-ACCESS  read-create
    STATUS      current
    DESCRIPTION
        "Use the specified network address as a classification criterion. If a full
        classification expression is also specified, it is AND-ed with this network
        address criterion."
    ::= { ntcTrfShExtClassifEntry 4 }
    
ntcTrfShapeExtNetwAddr           OBJECT-TYPE
    SYNTAX      NtcNetworkAddress
    MAX-ACCESS  read-create
    STATUS      current
    DESCRIPTION
        "IP address and prefix to be used as a classification criterion. Only used when
        UseNetworkAddress is true."
    ::= { ntcTrfShExtClassifEntry 5 }
    
ntcTrfShapeExtExpr               OBJECT-TYPE
    SYNTAX      DisplayString (SIZE(0..1000))
    MAX-ACCESS  read-create
    STATUS      current
    DESCRIPTION
        "The classification expression to be matched against incoming traffic."
    ::= { ntcTrfShExtClassifEntry 6 }
    
ntcTrfShapeExtShapingNode        OBJECT-TYPE
    SYNTAX      DisplayString (SIZE(0..30))
    MAX-ACCESS  read-create
    STATUS      current
    DESCRIPTION
        "The name of the traffic shaping node."
    ::= { ntcTrfShExtClassifEntry 7 }
    
ntcTrfShapeExtMatchingOrder      OBJECT-TYPE
    SYNTAX      Unsigned32 (1..99)
    MAX-ACCESS  read-create
    STATUS      current
    DESCRIPTION
        "Use the specified matching order for the classification criterion. The
        matching order defines the order in which packets are processed by the
        classification rules. This is important for disambiguation when multiple
        classification rules match the same packet. The order ranges from 1 (match
        first) to 99 (match last)."
    ::= { ntcTrfShExtClassifEntry 8 }
    
ntcTrfShExtShapingNodeTable      OBJECT-TYPE
    SYNTAX      SEQUENCE OF NtcTrfShExtShapingNodeEntry
    MAX-ACCESS  not-accessible
    STATUS      current
    DESCRIPTION
        "A table containing the ntcTrfShExtShapingNode"
    ::= { ntcTrfShapeObjects 7 }

ntcTrfShExtShapingNodeEntry      OBJECT-TYPE
    SYNTAX      NtcTrfShExtShapingNodeEntry
    MAX-ACCESS  not-accessible
    STATUS      current
    DESCRIPTION
        "A conceptual row of the ntcTrfShExtShapingNodeTable."
    INDEX   { ntcTrfShExtShapingNodeName  }
    ::= { ntcTrfShExtShapingNodeTable 1 }

NtcTrfShExtShapingNodeEntry      ::= SEQUENCE {
    ntcTrfShExtShapingNodeName         DisplayString,
    ntcTrfShExtShapingNodeRowStatus    RowStatus,
    ntcTrfShExtShapingNodeEnable       NtcEnable,
    ntcTrfShapeExtParentNam            DisplayString,
    ntcTrfShapeExtCir                  Unsigned32,
    ntcTrfShapeExtPir                  Unsigned32,
    ntcTrfShapeExtDestChan             DisplayString,
    ntcTrfShapeExtPrio                 Unsigned32,
    ntcTrfMaxQTExtime                  Unsigned32,
    ntcTrfShapeUnit                    INTEGER
    }
    
ntcTrfShExtShapingNodeName       OBJECT-TYPE
    SYNTAX      DisplayString (SIZE(1..30))
    MAX-ACCESS  not-accessible
    STATUS      current
    DESCRIPTION
        "The name of the traffic shaping node."
    ::= { ntcTrfShExtShapingNodeEntry 1 }
    
ntcTrfShExtShapingNodeRowStatus  OBJECT-TYPE
    SYNTAX      RowStatus
    MAX-ACCESS  read-create
    STATUS      current
    DESCRIPTION
        "The status of this conceptual row. An existing conceptual row can be in any
        one of the three states, 'notReady', 'notInService', or 'active'. If the
        manager wishes to add a row in a single shot with values for all the columns,
        the status column should be given as 'createAndGo(4)'. After the creation of a
        row, its value is set to active(1). If a row has to be created with values for
        only some columns, the status column should be 'createAndWait(5)'. Also, this
        row with partially filled columns has the status 'notReady(3)'. The entry
        remains in this state until the values for all the columns is set. After all
        the values are set, the agent changes this value to active(1).'"
    ::= { ntcTrfShExtShapingNodeEntry 2 }
    
ntcTrfShExtShapingNodeEnable     OBJECT-TYPE
    SYNTAX      NtcEnable
    MAX-ACCESS  read-create
    STATUS      current
    DESCRIPTION
        "Enable or disable the corresponding shaping node."
    ::= { ntcTrfShExtShapingNodeEntry 3 }
    
ntcTrfShapeExtParentNam          OBJECT-TYPE
    SYNTAX      DisplayString (SIZE(0..30))
    MAX-ACCESS  read-create
    STATUS      current
    DESCRIPTION
        "The name of the parent node of this traffic shaping node."
    ::= { ntcTrfShExtShapingNodeEntry 4 }
    
ntcTrfShapeExtCir                OBJECT-TYPE
    SYNTAX      Unsigned32
    MAX-ACCESS  read-create
    STATUS      current
    DESCRIPTION
        "Define the guaranteed information rate (CIR) for this shaping node."
    ::= { ntcTrfShExtShapingNodeEntry 5 }
    
ntcTrfShapeExtPir                OBJECT-TYPE
    SYNTAX      Unsigned32
    MAX-ACCESS  read-create
    STATUS      current
    DESCRIPTION
        "Define the peak information rate (PIR) for this shaping node."
    ::= { ntcTrfShExtShapingNodeEntry 6 }
    
ntcTrfShapeExtDestChan           OBJECT-TYPE
    SYNTAX      DisplayString (SIZE(0..100))
    MAX-ACCESS  read-create
    STATUS      current
    DESCRIPTION
        "The name of the destination channel for this shaping rule. This is defined in
        another functional block. (e.g. MPE, GSE, ...)"
    ::= { ntcTrfShExtShapingNodeEntry 7 }
    
ntcTrfShapeExtPrio               OBJECT-TYPE
    SYNTAX      Unsigned32
    MAX-ACCESS  read-create
    STATUS      current
    DESCRIPTION
        "Define the priority for this shaping node when dividing rate between nodes."
    ::= { ntcTrfShExtShapingNodeEntry 8 }
    
ntcTrfMaxQTExtime                OBJECT-TYPE
    SYNTAX      Unsigned32
    UNITS       "ms"
    MAX-ACCESS  read-create
    STATUS      current
    DESCRIPTION
        "The maximum time packets are allowed to remain in a shaping queue before being
        dropped."
    ::= { ntcTrfShExtShapingNodeEntry 9 }
    
ntcTrfShapeUnit                  OBJECT-TYPE
    SYNTAX      INTEGER { bitrate(0), symbolrate(1) }
    MAX-ACCESS  read-create
    STATUS      current
    DESCRIPTION
        "Shaping Unit."
    ::= { ntcTrfShExtShapingNodeEntry 10 }
    

--
--  Module Conformance
--

ntcTrfShapeConfGrpV1Standard     OBJECT-GROUP
    OBJECTS    {
                   ntcTrfShEnable,
                   ntcTrfShInputSelection,
                   ntcTrfShapeClassifName,
                   ntcTrfShClassificationEnable,
                   ntcTrfShapeUseNetwAddress,
                   ntcTrfShapeNetwAddress,
                   ntcTrfShapeExpr,
                   ntcTrfShapeShapingNode,
                   ntcTrfShapeNodeName,
                   ntcTrfShShapingNodeEnable,
                   ntcTrfShapeParentName,
                   ntcTrfShapeCir,
                   ntcTrfShapePir,
                   ntcTrfShapeDestChannel,
                   ntcTrfShapePrio,
                   ntcTrfMaxQTime,
                   ntcTrfShMonFwdBytes,
                   ntcTrfShMonFwdPackets,
                   ntcTrfShMonDropBytes,
                   ntcTrfShMonDropPackets,
                   ntcTrfMonShNodeName,
                   ntcTrfMonShNodeFwdByte,
                   ntcTfrMonShNodeFwdPackets,
                   ntcTrfMonShNodeDropByt,
                   ntcTrfShapeNodeDropPackets,
                   ntcTrfShapeNodeAverageDelay,
                   ntcTrfShapeNodeVolRate,
                   ntcTrfShapeNodeDropRate,
                   ntcTrfShapeNodeVolUnit,
                   ntcTrfShMonReset,
                   ntcTrfShMonFwdBitRate,
                   ntcTrfShExtClassifRowStatus,
                   ntcTrfShExtClassifEnable,
                   ntcTrfShapeExtUseNetwAddr,
                   ntcTrfShapeExtNetwAddr,
                   ntcTrfShapeExtExpr,
                   ntcTrfShapeExtShapingNode,
                   ntcTrfShapeExtMatchingOrder,
                   ntcTrfShExtShapingNodeRowStatus,
                   ntcTrfShExtShapingNodeEnable,
                   ntcTrfShapeExtParentNam,
                   ntcTrfShapeExtCir,
                   ntcTrfShapeExtPir,
                   ntcTrfShapeExtDestChan,
                   ntcTrfShapeExtPrio,
                   ntcTrfMaxQTExtime,
                   ntcTrfShapeUnit
               }
    STATUS      current
    DESCRIPTION
        "Managed objects that constitute version 1 of a system device with standard capabilities."
    ::= { ntcTrfShapeConfGroup 1}
    
ntcTrfShapeConfCompV1Standard    MODULE-COMPLIANCE
    STATUS      current
    DESCRIPTION
        "Compliance statement for Newtec device MIB implementations."
    MODULE  -- this module
    MANDATORY-GROUPS
                  {
                      ntcTrfShapeConfGrpV1Standard
                  }
    ::= { ntcTrfShapeConfCompliance  1 }
    

END
