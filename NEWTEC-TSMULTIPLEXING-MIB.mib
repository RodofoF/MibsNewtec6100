NEWTEC-TSMULTIPLEXING-MIB DEFINITIONS ::= BEGIN

IMPORTS
    Counter32,
    Unsigned32,
    MODULE-IDENTITY,
    OBJECT-IDENTITY,
    OBJECT-TYPE
        FROM SNMPv2-SMI

    MODULE-COMPLIANCE,
    OBJECT-GROUP
        FROM SNMPv2-CONF
    
    Float32TC
        FROM FLOAT-TC-MIB

    NtcAlarmState,
    NtcEnable
        FROM NEWTEC-TC-MIB

    DisplayString
        FROM SNMPv2-TC

    ntcFunction
        FROM NEWTEC-MAIN-MIB;


--
--  Module Identification
--

ntcTsMultiplexing   MODULE-IDENTITY
    LAST-UPDATED "201602020700Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular MIB containing definitions for transport stream multiplexing
        functionality."

    REVISION  "201602020700Z"
    DESCRIPTION
        "ntcTsMuxAlmBufferOverflow and enum protectedTsOverIp added"
    REVISION  "201409090900Z"
    DESCRIPTION
        "Descriptions adapted"
    REVISION  "201309201000Z"
    DESCRIPTION
        "overflow alarm added for M6100 R1.4"
    REVISION  "201303271000Z"
    DESCRIPTION
        "Release for M6100 R1.3"
    REVISION  "201206281200Z"
    DESCRIPTION
        "Release for M6100 R1.2"
    ::= { ntcFunction  1600 }
    

--
-- Top-Level Structure
--

-- ntcTsMultiplexing content

ntcTsMuxObjects                  OBJECT-IDENTITY
    STATUS        current
    DESCRIPTION   "Container holding ntcTsMuxObjects definitions."
    ::= { ntcTsMultiplexing 1 }
    
ntcTsMuxConformance              OBJECT-IDENTITY
    STATUS        current
    DESCRIPTION   "Conformance requirements."
    ::= { ntcTsMultiplexing 2 }
    
-- ntcTsMuxObjects content

ntcTsMuxRateAdapter              OBJECT-IDENTITY
    STATUS        current
    DESCRIPTION   "Container holding ntcTsMuxRateAdapter definitions."
    ::= { ntcTsMuxObjects 2 }
    
ntcTsMuxMonitor                  OBJECT-IDENTITY
    STATUS        current
    DESCRIPTION   "Container holding ntcTsMuxMonitor definitions."
    ::= { ntcTsMuxObjects 3 }
    
ntcTsMuxCarrierId                OBJECT-IDENTITY
    STATUS        current
    DESCRIPTION   "Container holding ntcTsMuxCarrierId definitions."
    ::= { ntcTsMuxObjects 4 }
    
ntcTsMuxSignalling               OBJECT-IDENTITY
    STATUS        current
    DESCRIPTION   "Container holding ntcTsMuxSignalling definitions."
    ::= { ntcTsMuxObjects 5 }
    
ntcTsMuxAlarm                    OBJECT-IDENTITY
    STATUS        current
    DESCRIPTION   "Container holding ntcTsMuxAlarm definitions."
    ::= { ntcTsMuxObjects 6 }
    
-- ntcTsMuxConformance content

ntcTsMuxConfCompliance           OBJECT-IDENTITY
    STATUS        current
    DESCRIPTION   "Device compliance statements."
    ::= { ntcTsMuxConformance 1 }
    
ntcTsMuxConfGroup                OBJECT-IDENTITY
    STATUS        current
    DESCRIPTION   "Groups used by device compliance statements."
    ::= { ntcTsMuxConformance 2 }
    

--
-- Managed Objects
--

ntcInputSelectionTable           OBJECT-TYPE
    SYNTAX      SEQUENCE OF NtcInputSelectionEntry
    MAX-ACCESS  not-accessible
    STATUS      deprecated
    DESCRIPTION
        "A table containing the ntcInputSelection"
    ::= { ntcTsMuxObjects 1 }

ntcInputSelectionEntry           OBJECT-TYPE
    SYNTAX      NtcInputSelectionEntry
    MAX-ACCESS  not-accessible
    STATUS      deprecated
    DESCRIPTION
        "A conceptual row of the ntcInputSelectionTable."
    INDEX   { ntcInputSelectionInputType  }
    ::= { ntcInputSelectionTable 1 }

NtcInputSelectionEntry           ::= SEQUENCE {
    ntcInputSelectionInputType    INTEGER,
    ntcInputSelectionEnable       NtcEnable
    }
    
ntcInputSelectionInputType       OBJECT-TYPE
    SYNTAX      INTEGER { asi(0), tsOverIp(1), mpe(2), prbs(3), protectedTsOverIp(4) }
    MAX-ACCESS  not-accessible
    STATUS      deprecated
    DESCRIPTION
        "The input type"
    ::= { ntcInputSelectionEntry 1 }
    
ntcInputSelectionEnable          OBJECT-TYPE
    SYNTAX      NtcEnable
    MAX-ACCESS  read-write
    STATUS      deprecated
    DESCRIPTION
        "Enable or disable the corresponding input type. This is deprecated, and is
        internally synced to the status of the individual input blocks."
    DEFVAL { off }
    ::= { ntcInputSelectionEntry 2 }
    
ntcTsMuxRaEnable                 OBJECT-TYPE
    SYNTAX      NtcEnable
    MAX-ACCESS  read-write
    STATUS      current
    DESCRIPTION
        "Enable or disable the TS stream Rate Adapter. Null packets will be introduced
        to match the input rate (ASI or TS over IP) with the modulator TS Rate."
    DEFVAL { on }
    ::= { ntcTsMuxRateAdapter 1 }
    
ntcTsMuxRaNullPktDrop            OBJECT-TYPE
    SYNTAX      NtcEnable
    MAX-ACCESS  read-write
    STATUS      current
    DESCRIPTION
        "Enable or disable Null Packet Drop when the Rate Adaptor is enabled. This
        option will delete all null packets from the TS stream and reinserts new null
        packets to match the interface rate of the modulator board. This mode allows
        rate adaptation to higher and lower rates."
    DEFVAL { on }
    ::= { ntcTsMuxRateAdapter 2 }
    
ntcTsMuxRaPcrRestamp             OBJECT-TYPE
    SYNTAX      NtcEnable
    MAX-ACCESS  read-write
    STATUS      current
    DESCRIPTION
        "Enable or disable PCR (Program Clock Reference) Restamping when Rate Adaptor
        functionality is enabled."
    DEFVAL { on }
    ::= { ntcTsMuxRateAdapter 3 }
    
ntcTsMuxMonResetCounters         OBJECT-TYPE
    SYNTAX      INTEGER { counting(0), reset(1) }
    MAX-ACCESS  read-write
    STATUS      current
    DESCRIPTION
        "Reset the traffic counters."
    DEFVAL { counting }
    ::= { ntcTsMuxMonitor 1 }
    
ntcTsMuxMonStatisticsTable       OBJECT-TYPE
    SYNTAX      SEQUENCE OF NtcTsMuxMonStatisticsEntry
    MAX-ACCESS  not-accessible
    STATUS      current
    DESCRIPTION
        "A table containing the ntcTsMuxMonStatistics"
    ::= { ntcTsMuxMonitor 2 }

ntcTsMuxMonStatisticsEntry       OBJECT-TYPE
    SYNTAX      NtcTsMuxMonStatisticsEntry
    MAX-ACCESS  not-accessible
    STATUS      current
    DESCRIPTION
        "A conceptual row of the ntcTsMuxMonStatisticsTable."
    INDEX   { ntcTsMuxMonStatisticsType  }
    ::= { ntcTsMuxMonStatisticsTable 1 }

NtcTsMuxMonStatisticsEntry       ::= SEQUENCE {
    ntcTsMuxMonStatisticsType    INTEGER,
    ntcTsMuxMonPacketCount       Counter32,
    ntcTsMuxMonPacketRate        Counter32,
    ntcTsMuxMonBitRatet          Counter32,
    ntcTsMuxMonBWOccopation      Unsigned32
    }
    
ntcTsMuxMonStatisticsType        OBJECT-TYPE
    SYNTAX      INTEGER { asi(0), tsOverIp(1), mpe(2), inputNullPackets(3), signalling(4), outputNullPackets(5), outputDataPackets(6), outputTotalPackets(7), protectedTsOverIp(8) }
    MAX-ACCESS  not-accessible
    STATUS      current
    DESCRIPTION
        "The traffic type of the different counters."
    ::= { ntcTsMuxMonStatisticsEntry 1 }
    
ntcTsMuxMonPacketCount           OBJECT-TYPE
    SYNTAX      Counter32
    UNITS       "packets"
    MAX-ACCESS  read-only
    STATUS      current
    DESCRIPTION
        "Total number of packets."
    ::= { ntcTsMuxMonStatisticsEntry 2 }
    
ntcTsMuxMonPacketRate            OBJECT-TYPE
    SYNTAX      Counter32
    UNITS       "pps"
    MAX-ACCESS  read-only
    STATUS      current
    DESCRIPTION
        "TS packet Rate."
    ::= { ntcTsMuxMonStatisticsEntry 3 }
    
ntcTsMuxMonBitRatet              OBJECT-TYPE
    SYNTAX      Counter32
    UNITS       "bps"
    MAX-ACCESS  read-only
    STATUS      current
    DESCRIPTION
        "Bit Rate."
    ::= { ntcTsMuxMonStatisticsEntry 4 }
    
ntcTsMuxMonBWOccopation          OBJECT-TYPE
    SYNTAX      Unsigned32 (0..100)
    UNITS       "%"
    MAX-ACCESS  read-only
    STATUS      current
    DESCRIPTION
        "Usage expressed in percentage of the total output Bandwidth."
    ::= { ntcTsMuxMonStatisticsEntry 5 }
    
ntcTsMuxCarIdEnable              OBJECT-TYPE
    SYNTAX      NtcEnable
    MAX-ACCESS  read-write
    STATUS      current
    DESCRIPTION
        "Enable or disable the carrier ID."
    DEFVAL { off }
    ::= { ntcTsMuxCarrierId 1 }
    
ntcTsMuxCarIdDescriptorTag       OBJECT-TYPE
    SYNTAX      Unsigned32 (192..254)
    MAX-ACCESS  read-write
    STATUS      current
    DESCRIPTION
        "Descriptor Tag"
    DEFVAL { 196 }
    ::= { ntcTsMuxCarrierId 2 }
    
ntcTsMuxCarIdModMfg              OBJECT-TYPE
    SYNTAX      DisplayString (SIZE(0..5))
    MAX-ACCESS  read-only
    STATUS      current
    DESCRIPTION
        "Name of modulator manufacturer"
    ::= { ntcTsMuxCarrierId 3 }
    
ntcTsMuxCarIdModSerialNr         OBJECT-TYPE
    SYNTAX      DisplayString (SIZE(0..12))
    MAX-ACCESS  read-only
    STATUS      current
    DESCRIPTION
        "Electronic serial number of modulator"
    ::= { ntcTsMuxCarrierId 4 }
    
ntcTsMuxCarIdCarrierIdentifier   OBJECT-TYPE
    SYNTAX      DisplayString (SIZE(0..5))
    MAX-ACCESS  read-write
    STATUS      current
    DESCRIPTION
        "Name of carrier company"
    ::= { ntcTsMuxCarrierId 5 }
    
ntcTsMuxCarIdTelephoneNr         OBJECT-TYPE
    SYNTAX      DisplayString (SIZE(0..17))
    MAX-ACCESS  read-write
    STATUS      current
    DESCRIPTION
        "Operators telephone number"
    ::= { ntcTsMuxCarrierId 6 }
    
ntcTsMuxCarIdLongitude           OBJECT-TYPE
    SYNTAX      Float32TC
    MAX-ACCESS  read-write
    STATUS      current
    DESCRIPTION
        "Geo coordinates of encoder (longitude from +000.0000 to +/-180.0000)"
    DEFVAL { '00000000'H }
    ::= { ntcTsMuxCarrierId 7 }
    
ntcTsMuxCarIdLatitude            OBJECT-TYPE
    SYNTAX      Float32TC
    MAX-ACCESS  read-write
    STATUS      current
    DESCRIPTION
        "Geo coordinates of encoder (latitude from +00.0000 to +/-90.0000)"
    DEFVAL { '00000000'H }
    ::= { ntcTsMuxCarrierId 8 }
    
ntcTsMuxCarIdUserInfo            OBJECT-TYPE
    SYNTAX      DisplayString (SIZE(0..15))
    MAX-ACCESS  read-write
    STATUS      current
    DESCRIPTION
        "Custom user information"
    ::= { ntcTsMuxCarrierId 9 }
    
ntcTsMuxCarIdLongitudeString     OBJECT-TYPE
    SYNTAX      DisplayString (SIZE(1..9))
    MAX-ACCESS  read-write
    STATUS      current
    DESCRIPTION
        "Geo coordinates of encoder (longitude from +000.0000 to +/-180.0000)"
    DEFVAL { "0.0000" }
    ::= { ntcTsMuxCarrierId 10 }
    
ntcTsMuxCarIdLatitudeString      OBJECT-TYPE
    SYNTAX      DisplayString (SIZE(1..9))
    MAX-ACCESS  read-write
    STATUS      current
    DESCRIPTION
        "Geo coordinates of encoder (latitude from +00.0000 to +/-90.0000)"
    DEFVAL { "0.0000" }
    ::= { ntcTsMuxCarrierId 11 }
    
ntcTsMuxSigNetworkId             OBJECT-TYPE
    SYNTAX      Unsigned32 (0..65535)
    MAX-ACCESS  read-write
    STATUS      current
    DESCRIPTION
        "Network Identifier of the originating delivery system."
    DEFVAL { 0 }
    ::= { ntcTsMuxSignalling 1 }
    
ntcTsMuxSigTransportStreamId     OBJECT-TYPE
    SYNTAX      Unsigned32 (0..65535)
    MAX-ACCESS  read-write
    STATUS      current
    DESCRIPTION
        "Transport Stream Identifier of the originating delivery system."
    DEFVAL { 0 }
    ::= { ntcTsMuxSignalling 2 }
    
ntcTsMuxSigPatRepetitionRate     OBJECT-TYPE
    SYNTAX      Unsigned32 (25..500)
    UNITS       "ms"
    MAX-ACCESS  read-write
    STATUS      current
    DESCRIPTION
        "Program Allocation Table repetition rate in milliseconds."
    DEFVAL { 400 }
    ::= { ntcTsMuxSignalling 3 }
    
ntcTsMuxSigSdtRepetitionRate     OBJECT-TYPE
    SYNTAX      Unsigned32 (25..2000)
    UNITS       "ms"
    MAX-ACCESS  read-write
    STATUS      current
    DESCRIPTION
        "Service Descriptor Table repetition rate in milliseconds."
    DEFVAL { 500 }
    ::= { ntcTsMuxSignalling 4 }
    
ntcTsMuxSigPmtRepetitionRate     OBJECT-TYPE
    SYNTAX      Unsigned32 (25..500)
    UNITS       "ms"
    MAX-ACCESS  read-write
    STATUS      current
    DESCRIPTION
        "Program Map Table repetition rate in milliseconds."
    DEFVAL { 400 }
    ::= { ntcTsMuxSignalling 5 }
    
ntcTsMuxAlmLocalPidOnInput       OBJECT-TYPE
    SYNTAX      NtcAlarmState
    MAX-ACCESS  read-only
    STATUS      current
    DESCRIPTION
        "This alarm is raised when a local generated packet is using a PID which
        already is available on the input of the device. In case of error no data
        encapsulation will be supported. This variable indicates the current status of
        the alarm."
    ::= { ntcTsMuxAlarm 1 }
    
ntcTsMuxAlmSignalTableProcError  OBJECT-TYPE
    SYNTAX      NtcAlarmState
    MAX-ACCESS  read-only
    STATUS      current
    DESCRIPTION
        "This alarm is raised when a local generated table is using a program number
        which is already in use by the MPEG stream. In an error case no data
        encapsulation will be supported. This variable indicates the current status of
        the alarm."
    ::= { ntcTsMuxAlarm 2 }
    
ntcTsMuxAlmSignalOverflow        OBJECT-TYPE
    SYNTAX      NtcAlarmState
    MAX-ACCESS  read-only
    STATUS      current
    DESCRIPTION
        "This alarm is raised when the input signalling buffer of the modulator is
        full. This variable indicates the current status of the alarm."
    ::= { ntcTsMuxAlarm 3 }
    
ntcTsMuxAlmBufferOverflow        OBJECT-TYPE
    SYNTAX      NtcAlarmState
    MAX-ACCESS  read-only
    STATUS      current
    DESCRIPTION
        "This alarm is raised when over-sending TS rate adapter. This variable
        indicates the current status of the alarm."
    ::= { ntcTsMuxAlarm 4 }
    

--
--  Module Conformance
--

ntcTsMuxConfGrpV1Standard        OBJECT-GROUP
    OBJECTS    {
                   ntcTsMuxRaEnable,
                   ntcTsMuxRaNullPktDrop,
                   ntcTsMuxRaPcrRestamp,
                   ntcTsMuxMonResetCounters,
                   ntcTsMuxMonPacketCount,
                   ntcTsMuxMonPacketRate,
                   ntcTsMuxMonBitRatet,
                   ntcTsMuxMonBWOccopation,
                   ntcTsMuxCarIdEnable,
                   ntcTsMuxCarIdDescriptorTag,
                   ntcTsMuxCarIdModMfg,
                   ntcTsMuxCarIdModSerialNr,
                   ntcTsMuxCarIdCarrierIdentifier,
                   ntcTsMuxCarIdTelephoneNr,
                   ntcTsMuxCarIdLongitude,
                   ntcTsMuxCarIdLatitude,
                   ntcTsMuxCarIdUserInfo,
                   ntcTsMuxCarIdLongitudeString,
                   ntcTsMuxCarIdLatitudeString,
                   ntcTsMuxSigNetworkId,
                   ntcTsMuxSigTransportStreamId,
                   ntcTsMuxSigPatRepetitionRate,
                   ntcTsMuxSigSdtRepetitionRate,
                   ntcTsMuxSigPmtRepetitionRate,
                   ntcTsMuxAlmLocalPidOnInput,
                   ntcTsMuxAlmSignalTableProcError,
                   ntcTsMuxAlmSignalOverflow,
                   ntcTsMuxAlmBufferOverflow
               }
    STATUS      current
    DESCRIPTION
        "Managed objects that constitute version 1 of a system device with standard capabilities."
    ::= { ntcTsMuxConfGroup 1}
    
ntcTsMuxConfGrpObsolete          OBJECT-GROUP
    OBJECTS    {
                   ntcInputSelectionEnable
               }
    STATUS      obsolete
    DESCRIPTION
        "Managed objects which are deprecated or obsolete"
    ::= { ntcTsMuxConfGroup 2}
    
ntcTsMuxConfCompV1Standard       MODULE-COMPLIANCE
    STATUS      current
    DESCRIPTION
        "Compliance statement for Newtec device MIB implementations."
    MODULE  -- this module
    MANDATORY-GROUPS
                  {
                      ntcTsMuxConfGrpV1Standard
                  }
    ::= { ntcTsMuxConfCompliance  1 }
    

END
