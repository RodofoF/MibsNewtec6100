NEWTEC-ASIIN-MIB DEFINITIONS ::= BEGIN

IMPORTS
    Unsigned32,
    Counter32,
    MODULE-IDENTITY,
    OBJECT-IDENTITY,
    OBJECT-TYPE
        FROM SNMPv2-SMI

    MODULE-COMPLIANCE,
    OBJECT-GROUP
        FROM SNMPv2-CONF
    
    Float32TC
        FROM FLOAT-TC-MIB

    NtcAlarmState,
    NtcEnable,
    NtcPid
        FROM NEWTEC-TC-MIB

    ntcFunction
        FROM NEWTEC-MAIN-MIB;


--
--  Module Identification
--

ntcAsiIn   MODULE-IDENTITY
    LAST-UPDATED "201409090900Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular ASI input MIB containing definitions for ASI input
        functionality."

    REVISION  "201409090900Z"
    DESCRIPTION
        "Descriptions adapted"
    REVISION  "201206281200Z"
    DESCRIPTION
        "Release for M6100 R1.2"
    ::= { ntcFunction  800 }
    

--
-- Top-Level Structure
--

-- ntcAsiIn content

ntcAsiInObjects                  OBJECT-IDENTITY
    STATUS        current
    DESCRIPTION   "Container holding ntcAsiInObjects definitions."
    ::= { ntcAsiIn 1 }
    
ntcAsiInConformance              OBJECT-IDENTITY
    STATUS        current
    DESCRIPTION   "Conformance requirements."
    ::= { ntcAsiIn 2 }
    
-- ntcAsiInObjects content

ntcAsiInPrbsGenerator            OBJECT-IDENTITY
    STATUS        current
    DESCRIPTION   "Container holding ntcAsiInPrbsGenerator definitions."
    ::= { ntcAsiInObjects 7 }
    
ntcAsiInPrbsMonitor              OBJECT-IDENTITY
    STATUS        current
    DESCRIPTION   "Container holding ntcAsiInPrbsMonitor definitions."
    ::= { ntcAsiInObjects 8 }
    
ntcAsiInAlarm                    OBJECT-IDENTITY
    STATUS        current
    DESCRIPTION   "Container holding ntcAsiInAlarm definitions."
    ::= { ntcAsiInObjects 9 }
    
-- ntcAsiInConformance content

ntcAsiInConfCompliance           OBJECT-IDENTITY
    STATUS        current
    DESCRIPTION   "Device compliance statements."
    ::= { ntcAsiInConformance 1 }
    
ntcAsiInConfGroup                OBJECT-IDENTITY
    STATUS        current
    DESCRIPTION   "Groups used by device compliance statements."
    ::= { ntcAsiInConformance 2 }
    

--
-- Managed Objects
--

ntcAsiInInputSelection           OBJECT-TYPE
    SYNTAX      INTEGER { none(0), asi1(1), asi2(2), asi1or2(40), asi1before2(41), asi2before1(42), prbsgenerator(100) }
    MAX-ACCESS  read-write
    STATUS      current
    DESCRIPTION
        "Configuration of the ASI external input interface."
    DEFVAL { none }
    ::= { ntcAsiInObjects 1 }
    
ntcAsiInActiveInput              OBJECT-TYPE
    SYNTAX      INTEGER { off(0), asi1(1), asi2(2) }
    MAX-ACCESS  read-only
    STATUS      current
    DESCRIPTION
        "Displays the active ASI input interface. When PRBS is selected it will
        indicate 'off'."
    ::= { ntcAsiInObjects 2 }
    
ntcAsiInInlineSplitter           OBJECT-TYPE
    SYNTAX      INTEGER { none(0), e3dBSplitter(1), e6dBSplitter(2) }
    MAX-ACCESS  read-write
    STATUS      current
    DESCRIPTION
        "Variable to configure the presence of an external in-line splitter with a
        given loss."
    DEFVAL { none }
    ::= { ntcAsiInObjects 3 }
    
ntcAsiInMeasuredInputTsBitRate   OBJECT-TYPE
    SYNTAX      Unsigned32
    UNITS       "bps"
    MAX-ACCESS  read-only
    STATUS      current
    DESCRIPTION
        "Displays the measured ASI interface input rate in bps."
    ::= { ntcAsiInObjects 4 }
    
ntcAsiInInputFraming             OBJECT-TYPE
    SYNTAX      INTEGER { ts188(0), ts204(1) }
    MAX-ACCESS  read-write
    STATUS      current
    DESCRIPTION
        "Configuration of the ASI input framing type.
        - 188-byte packets
        - 204-byte packets (188 data bytes and 16 dummy bytes). Before transmission,
        these 16 bytes are ignored and replaced by newly calculated Reed-Solomon
        parity bytes."
    DEFVAL { ts188 }
    ::= { ntcAsiInObjects 5 }
    
ntcAsiInInputIfSwitchCount       OBJECT-TYPE
    SYNTAX      Counter32
    MAX-ACCESS  read-only
    STATUS      current
    DESCRIPTION
        "Counts the number of times the device switched to another ASI input interface."
    ::= { ntcAsiInObjects 6 }
    
ntcAsiInPrbsGenTsBitRate         OBJECT-TYPE
    SYNTAX      Unsigned32
    UNITS       "bps"
    MAX-ACCESS  read-write
    STATUS      current
    DESCRIPTION
        "The PRBS (Pseudo Random Binary Sequence) generator TS Bit Rate in bps."
    DEFVAL { 1000000 }
    ::= { ntcAsiInPrbsGenerator 1 }
    
ntcAsiInPrbsGenType              OBJECT-TYPE
    SYNTAX      INTEGER { prbs(0), counter(1) }
    MAX-ACCESS  read-write
    STATUS      current
    DESCRIPTION
        "
        - PRBS : Configures the test generator to generate transport stream packets
        containing PRBS data. The generated PRBS complies with HP3764 Compatible
        2^23-1 PRBS sequence as specified in CCITT Rec. 0.151.
        - Counter : Configures the test generator to generate transport stream packets
        containing 8-bit counter values as data. This counter data can not be analyzed
        by the test detector. It can only be used for manual verification by an
        external analyzer."
    DEFVAL { prbs }
    ::= { ntcAsiInPrbsGenerator 2 }
    
ntcAsiInPrbsGenPidHandling       OBJECT-TYPE
    SYNTAX      NtcEnable
    MAX-ACCESS  read-write
    STATUS      current
    DESCRIPTION
        "Configuration of the PID (Packet Identifier) handling in the PRBS Generator.
        Configuration of the test generator to generate transport stream packets with
        a valid transport stream header. The configured PID is inserted in the
        transport stream header and the continuity counter is incrementing. Possible
        settings;
        - Off: Transport stream packets are generated without a valid transport stream
        header. In this case, a 0x47 sync marker is generated followed by 187 test
        bytes.
        - On: When enabled, transport stream packets are generated with a configurable
        PID. (A burst of TS packets will be generated with a configurable of number
        data packets and a configurable number of null packets.)"
    DEFVAL { off }
    ::= { ntcAsiInPrbsGenerator 3 }
    
ntcAsiInPrbsGenPidValue          OBJECT-TYPE
    SYNTAX      Unsigned32 (0..8191)
    MAX-ACCESS  read-write
    STATUS      current
    DESCRIPTION
        "Configure the PRBS generator packet PID value."
    DEFVAL { 1 }
    ::= { ntcAsiInPrbsGenerator 4 }
    
ntcAsiInPrbsGenNumberDataPkt     OBJECT-TYPE
    SYNTAX      Unsigned32 (1..4294967295)
    MAX-ACCESS  read-write
    STATUS      current
    DESCRIPTION
        "Configuration of the number of datapackets per burst. Current devices have an
        upper limit of 255 datapackets per burst."
    DEFVAL { 1 }
    ::= { ntcAsiInPrbsGenerator 5 }
    
ntcAsiInPrbsGenNumberNullPkt     OBJECT-TYPE
    SYNTAX      Unsigned32
    MAX-ACCESS  read-write
    STATUS      current
    DESCRIPTION
        "Configuration of the number of null packets per burst. Current devices have an
        upper limit of 255 but this may increase in the future."
    DEFVAL { 0 }
    ::= { ntcAsiInPrbsGenerator 6 }
    
ntcAsiInPrbsMonEnable            OBJECT-TYPE
    SYNTAX      NtcEnable
    MAX-ACCESS  read-write
    STATUS      current
    DESCRIPTION
        "Enable or disable the PRBS monitoring. When monitoring is enabled the
        statistics are displayed in the following parameters."
    DEFVAL { off }
    ::= { ntcAsiInPrbsMonitor 1 }
    
ntcAsiInPrbsMonPidHandling       OBJECT-TYPE
    SYNTAX      NtcEnable
    MAX-ACCESS  read-write
    STATUS      current
    DESCRIPTION
        "Detect/filter out the PID inside data packets of the PRBS monitor. This is
        reflected in the monitoring statistics."
    DEFVAL { off }
    ::= { ntcAsiInPrbsMonitor 2 }
    
ntcAsiInPrbsMonPidValue          OBJECT-TYPE
    SYNTAX      NtcPid
    MAX-ACCESS  read-write
    STATUS      current
    DESCRIPTION
        "Configuration of the PRBS monitor data packet PID value."
    DEFVAL { 1 }
    ::= { ntcAsiInPrbsMonitor 3 }
    
ntcAsiInPrbsMonState             OBJECT-TYPE
    SYNTAX      INTEGER { off(0), unsync(1), prbs(2), ais(3) }
    MAX-ACCESS  read-only
    STATUS      current
    DESCRIPTION
        "Displays the PRBS monitor status. Possible values are: Off, Unsync (no PRBS
        sync) and PRBS (PRBS sync)."
    ::= { ntcAsiInPrbsMonitor 4 }
    
ntcAsiInPrbsMonSyncSeconds       OBJECT-TYPE
    SYNTAX      Unsigned32
    MAX-ACCESS  read-only
    STATUS      current
    DESCRIPTION
        "Indicates how many seconds the PRBS monitor is synchronized to the PRBS
        stream."
    ::= { ntcAsiInPrbsMonitor 5 }
    
ntcAsiInPrbsMonErrorCount        OBJECT-TYPE
    SYNTAX      Counter32
    MAX-ACCESS  read-only
    STATUS      current
    DESCRIPTION
        "Number of errors detected in the PRBS stream."
    ::= { ntcAsiInPrbsMonitor 6 }
    
ntcAsiInPrbsMonErrorRate         OBJECT-TYPE
    SYNTAX      Unsigned32 (0..21474836470)
    MAX-ACCESS  read-only
    STATUS      current
    DESCRIPTION
        "Error rate detected in the PRBS stream. Float represented as unsigned integer
        is scaled by a factor of 10. i.e. a value of 100 in SNMP means an error rate
        of 10."
    ::= { ntcAsiInPrbsMonitor 7 }
    
ntcAsiInPrbsMonErrorRatio        OBJECT-TYPE
    SYNTAX      Float32TC
    MAX-ACCESS  read-only
    STATUS      current
    DESCRIPTION
        "Displays the error ratio detected in the PRBS stream."
    ::= { ntcAsiInPrbsMonitor 8 }
    
ntcAsiInAlmGeneralAsiInput       OBJECT-TYPE
    SYNTAX      NtcAlarmState
    MAX-ACCESS  read-only
    STATUS      current
    DESCRIPTION
        "This alarm is raised when there is a general ASI input alarm. This variable
        indicates the current status of the alarm."
    ::= { ntcAsiInAlarm 1 }
    
ntcAsiInAlmNoInputSignal         OBJECT-TYPE
    SYNTAX      NtcAlarmState
    MAX-ACCESS  read-only
    STATUS      current
    DESCRIPTION
        "This alarm is raised when no input signal is detected at the selected ASI
        input. This variable indicates the current status of the alarm."
    ::= { ntcAsiInAlarm 2 }
    
ntcAsiInAlmNoInputData           OBJECT-TYPE
    SYNTAX      NtcAlarmState
    MAX-ACCESS  read-only
    STATUS      current
    DESCRIPTION
        "This alarm is raised when no input data is detected at the selected ASI input.
        This variable indicates the current status of the alarm."
    ::= { ntcAsiInAlarm 3 }
    
ntcAsiInAlmInvalidTsBitRate      OBJECT-TYPE
    SYNTAX      NtcAlarmState
    MAX-ACCESS  read-only
    STATUS      current
    DESCRIPTION
        "This alarm is raised when the measured input Transport-Stream (TS) bitrate is
        higher or lower than the expected value. This variable indicates the current
        status of the alarm."
    ::= { ntcAsiInAlarm 4 }
    
ntcAsiInAlmBufferOverflow        OBJECT-TYPE
    SYNTAX      NtcAlarmState
    MAX-ACCESS  read-only
    STATUS      current
    DESCRIPTION
        "This alarm is raised when the input data buffer is full. This variable
        indicates the current status of the alarm."
    ::= { ntcAsiInAlarm 5 }
    
ntcAsiInAlmNoInputSignalAsi1     OBJECT-TYPE
    SYNTAX      NtcAlarmState
    MAX-ACCESS  read-only
    STATUS      current
    DESCRIPTION
        "This alarm is raised when no input signal is detected at the ASI1 input. This
        variable indicates the current status of the alarm."
    ::= { ntcAsiInAlarm 6 }
    
ntcAsiInAlmNoInputSignalAsi2     OBJECT-TYPE
    SYNTAX      NtcAlarmState
    MAX-ACCESS  read-only
    STATUS      current
    DESCRIPTION
        "This alarm is raised when no input signal is detected at the ASI2 input. This
        variable indicates the current status of the alarm."
    ::= { ntcAsiInAlarm 7 }
    
ntcAsiInAlmNoInputDataAsi1       OBJECT-TYPE
    SYNTAX      NtcAlarmState
    MAX-ACCESS  read-only
    STATUS      current
    DESCRIPTION
        "This alarm is raised when no input data is detected at the ASI1 input. This
        variable indicates the current status of the alarm."
    ::= { ntcAsiInAlarm 8 }
    
ntcAsiInAlmNoInputDataAsi2       OBJECT-TYPE
    SYNTAX      NtcAlarmState
    MAX-ACCESS  read-only
    STATUS      current
    DESCRIPTION
        "This alarm is raised when no input data is detected at the ASI2 input. This
        variable indicates the current status of the alarm."
    ::= { ntcAsiInAlarm 9 }
    

--
--  Module Conformance
--

ntcAsiInConfGrpV1Standard        OBJECT-GROUP
    OBJECTS    {
                   ntcAsiInInputSelection,
                   ntcAsiInActiveInput,
                   ntcAsiInInlineSplitter,
                   ntcAsiInMeasuredInputTsBitRate,
                   ntcAsiInInputFraming,
                   ntcAsiInInputIfSwitchCount,
                   ntcAsiInPrbsGenTsBitRate,
                   ntcAsiInPrbsGenType,
                   ntcAsiInPrbsGenPidHandling,
                   ntcAsiInPrbsGenPidValue,
                   ntcAsiInPrbsGenNumberDataPkt,
                   ntcAsiInPrbsGenNumberNullPkt,
                   ntcAsiInPrbsMonEnable,
                   ntcAsiInPrbsMonPidHandling,
                   ntcAsiInPrbsMonPidValue,
                   ntcAsiInPrbsMonState,
                   ntcAsiInPrbsMonSyncSeconds,
                   ntcAsiInPrbsMonErrorCount,
                   ntcAsiInPrbsMonErrorRate,
                   ntcAsiInPrbsMonErrorRatio,
                   ntcAsiInAlmGeneralAsiInput,
                   ntcAsiInAlmNoInputSignal,
                   ntcAsiInAlmNoInputData,
                   ntcAsiInAlmInvalidTsBitRate,
                   ntcAsiInAlmBufferOverflow,
                   ntcAsiInAlmNoInputSignalAsi1,
                   ntcAsiInAlmNoInputSignalAsi2,
                   ntcAsiInAlmNoInputDataAsi1,
                   ntcAsiInAlmNoInputDataAsi2
               }
    STATUS      current
    DESCRIPTION
        "Managed objects that constitute version 1 of a system device with standard capabilities."
    ::= { ntcAsiInConfGroup 1}
    
ntcAsiInConfCompV1Standard       MODULE-COMPLIANCE
    STATUS      current
    DESCRIPTION
        "Compliance statement for Newtec device MIB implementations."
    MODULE  -- this module
    MANDATORY-GROUPS
                  {
                      ntcAsiInConfGrpV1Standard
                  }
    ::= { ntcAsiInConfCompliance  1 }
    

END
