NEWTEC-PROTECTEDTSOVERIPIN-MIB DEFINITIONS ::= BEGIN

IMPORTS
    IpAddress,
    Unsigned32,
    Counter32,
    MODULE-IDENTITY,
    OBJECT-IDENTITY,
    OBJECT-TYPE
        FROM SNMPv2-SMI

    MODULE-COMPLIANCE,
    OBJECT-GROUP
        FROM SNMPv2-CONF
    
    NtcAlarmState,
    NtcEnable,
    NtcNetworkAddress
        FROM NEWTEC-TC-MIB

    DisplayString
        FROM SNMPv2-TC

    ntcFunction
        FROM NEWTEC-MAIN-MIB;


--
--  Module Identification
--

ntcProtectedTsOverIpIn   MODULE-IDENTITY
    LAST-UPDATED "201602020700Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular Protected TSoIP input MIB containing definitions for Protected
        TS over IP input functionality."

    REVISION  "201602020700Z"
    DESCRIPTION
        "initial release"
    ::= { ntcFunction  9400 }
    

--
-- Top-Level Structure
--

-- ntcProtectedTsOverIpIn content

ntcProtTsOIpInObjects            OBJECT-IDENTITY
    STATUS        current
    DESCRIPTION   "Container holding ntcProtTsOIpInObjects definitions."
    ::= { ntcProtectedTsOverIpIn 1 }
    
ntcProtTsOIpInConformance        OBJECT-IDENTITY
    STATUS        current
    DESCRIPTION   "Conformance requirements."
    ::= { ntcProtectedTsOverIpIn 2 }
    
-- ntcProtTsOIpInObjects content

ntcProtTsOIpInMon                OBJECT-IDENTITY
    STATUS        current
    DESCRIPTION   "Container holding ntcProtTsOIpInMon definitions."
    ::= { ntcProtTsOIpInObjects 4 }
    
ntcProtTsOIpInAlarms             OBJECT-IDENTITY
    STATUS        current
    DESCRIPTION   "Container holding ntcProtTsOIpInAlarms definitions."
    ::= { ntcProtTsOIpInObjects 5 }
    
ntcProtTsOIpInAlarm              OBJECT-IDENTITY
    STATUS        current
    DESCRIPTION   "Container holding ntcProtTsOIpInAlarm definitions."
    ::= { ntcProtTsOIpInObjects 6 }
    
-- ntcProtTsOIpInConformance content

ntcProtTsOIpInConfCompliance     OBJECT-IDENTITY
    STATUS        current
    DESCRIPTION   "Device compliance statements."
    ::= { ntcProtTsOIpInConformance 1 }
    
ntcProtTsOIpInConfGroup          OBJECT-IDENTITY
    STATUS        current
    DESCRIPTION   "Groups used by device compliance statements."
    ::= { ntcProtTsOIpInConformance 2 }
    

--
-- Managed Objects
--

ntcProtTsOIpInEnable             OBJECT-TYPE
    SYNTAX      NtcEnable
    MAX-ACCESS  read-write
    STATUS      current
    DESCRIPTION
        "Enable or disable TS (Transport Stream) over IP reception."
    DEFVAL { off }
    ::= { ntcProtTsOIpInObjects 1 }
    
ntcProtTsOIpInProtInpSelection   OBJECT-TYPE
    SYNTAX      INTEGER { tsoip1(1), tsoip2(2), tsoip1or2(3), tsoip1before2(4), tsoip2before1(5) }
    MAX-ACCESS  read-write
    STATUS      current
    DESCRIPTION
        "Configuration of the Protected TSoIP input interface."
    DEFVAL { tsoip1or2 }
    ::= { ntcProtTsOIpInObjects 2 }
    
ntcProtTsOIpInConfTable          OBJECT-TYPE
    SYNTAX      SEQUENCE OF NtcProtTsOIpInConfEntry
    MAX-ACCESS  not-accessible
    STATUS      current
    DESCRIPTION
        "Configuration table"
    ::= { ntcProtTsOIpInObjects 3 }

ntcProtTsOIpInConfEntry          OBJECT-TYPE
    SYNTAX      NtcProtTsOIpInConfEntry
    MAX-ACCESS  not-accessible
    STATUS      current
    DESCRIPTION
        "A conceptual row of the ntcProtTsOIpInConfTable."
    INDEX   { ntcProtTsOIpInConfName  }
    ::= { ntcProtTsOIpInConfTable 1 }

NtcProtTsOIpInConfEntry          ::= SEQUENCE {
    ntcProtTsOIpInConfName            DisplayString,
    ntcProtTsOIpInInpSelection        INTEGER,
    ntcProtTsOIpInTsEncapProtocol     INTEGER,
    ntcProtTsOIpInIpAddressType       INTEGER,
    ntcProtTsOIpInMulticastAddress    IpAddress,
    ntcProtTsOIpInMulticastSourceA    NtcNetworkAddress,
    ntcProtTsOIpInMulticastSourceB    NtcNetworkAddress,
    ntcProtTsOIpInUdpPort             Unsigned32,
    ntcProtTsOIpInTrafficProfile      INTEGER,
    ntcProtTsOIpInInputRateType       INTEGER,
    ntcProtTsOIpInAutoPcrDetection    NtcEnable,
    ntcProtTsOIpInPcrPid              Unsigned32,
    ntcProtTsOIpInMaxBufferDelay      Unsigned32,
    ntcProtTsOIpInInputTsBitRate      Unsigned32
    }
    
ntcProtTsOIpInConfName           OBJECT-TYPE
    SYNTAX      DisplayString (SIZE(1..32))
    MAX-ACCESS  not-accessible
    STATUS      current
    DESCRIPTION
        "Name of the configuration"
    ::= { ntcProtTsOIpInConfEntry 1 }
    
ntcProtTsOIpInInpSelection       OBJECT-TYPE
    SYNTAX      INTEGER { none(1), data1(2), data2(3), data(4), any(5) }
    MAX-ACCESS  read-write
    STATUS      current
    DESCRIPTION
        "Select the input interface for the TS over IP functionality."
    DEFVAL { none }
    ::= { ntcProtTsOIpInConfEntry 2 }
    
ntcProtTsOIpInTsEncapProtocol    OBJECT-TYPE
    SYNTAX      INTEGER { udp(0), rtp(1), rtpfec(2) }
    MAX-ACCESS  read-write
    STATUS      current
    DESCRIPTION
        "Encapsulation protocol used for the received TS over IP functionality (UDP,
        RTP and RTP with FEC)."
    DEFVAL { udp }
    ::= { ntcProtTsOIpInConfEntry 3 }
    
ntcProtTsOIpInIpAddressType      OBJECT-TYPE
    SYNTAX      INTEGER { unicast(0), multicast(1) }
    MAX-ACCESS  read-write
    STATUS      current
    DESCRIPTION
        "Configuration of the IP address type for TS over IP reception. (unicast or
        multicast)"
    DEFVAL { unicast }
    ::= { ntcProtTsOIpInConfEntry 4 }
    
ntcProtTsOIpInMulticastAddress   OBJECT-TYPE
    SYNTAX      IpAddress 
    MAX-ACCESS  read-write
    STATUS      current
    DESCRIPTION
        "Define the multicast IP address used to receive the TS over IP data
        functionality."
    DEFVAL { 'e0010001'h }
    ::= { ntcProtTsOIpInConfEntry 5 }
    
ntcProtTsOIpInMulticastSourceA   OBJECT-TYPE
    SYNTAX      NtcNetworkAddress
    MAX-ACCESS  read-write
    STATUS      current
    DESCRIPTION
        "Multicast source Address."
    DEFVAL { "0.0.0.0" }
    ::= { ntcProtTsOIpInConfEntry 6 }
    
ntcProtTsOIpInMulticastSourceB   OBJECT-TYPE
    SYNTAX      NtcNetworkAddress
    MAX-ACCESS  read-write
    STATUS      current
    DESCRIPTION
        "Multicast source Address."
    DEFVAL { "0.0.0.0" }
    ::= { ntcProtTsOIpInConfEntry 7 }
    
ntcProtTsOIpInUdpPort            OBJECT-TYPE
    SYNTAX      Unsigned32 (1..65535)
    MAX-ACCESS  read-write
    STATUS      current
    DESCRIPTION
        "Configure the UDP port on which the TS over IP stream is received."
    DEFVAL { 56789 }
    ::= { ntcProtTsOIpInConfEntry 8 }
    
ntcProtTsOIpInTrafficProfile     OBJECT-TYPE
    SYNTAX      INTEGER { vbr(0), cbr(1) }
    MAX-ACCESS  read-write
    STATUS      current
    DESCRIPTION
        "Configure the TS input traffic profile for the TS stream (CBR=constant or
        VBR=variable bitrate)."
    DEFVAL { cbr }
    ::= { ntcProtTsOIpInConfEntry 9 }
    
ntcProtTsOIpInInputRateType      OBJECT-TYPE
    SYNTAX      INTEGER { userdefined(0), pcr(1) }
    MAX-ACCESS  read-write
    STATUS      current
    DESCRIPTION
        "When the operator selects 'User Defined', the actual input rate and the
        control loop type needs to be specified further. In the other case, PCR PID
        and control loop type is used."
    DEFVAL { pcr }
    ::= { ntcProtTsOIpInConfEntry 10 }
    
ntcProtTsOIpInAutoPcrDetection   OBJECT-TYPE
    SYNTAX      NtcEnable
    MAX-ACCESS  read-write
    STATUS      current
    DESCRIPTION
        "Enable or disable Auto PCR Detection."
    DEFVAL { on }
    ::= { ntcProtTsOIpInConfEntry 11 }
    
ntcProtTsOIpInPcrPid             OBJECT-TYPE
    SYNTAX      Unsigned32 (0..8191)
    MAX-ACCESS  read-write
    STATUS      current
    DESCRIPTION
        "PCR PID."
    DEFVAL { 8191 }
    ::= { ntcProtTsOIpInConfEntry 12 }
    
ntcProtTsOIpInMaxBufferDelay     OBJECT-TYPE
    SYNTAX      Unsigned32
    UNITS       "ms"
    MAX-ACCESS  read-write
    STATUS      current
    DESCRIPTION
        "The maximum delay introduced by the device to compensate jitter introduced by
        the IP network. This is only relevant for CBR traffic."
    DEFVAL { 250 }
    ::= { ntcProtTsOIpInConfEntry 13 }
    
ntcProtTsOIpInInputTsBitRate     OBJECT-TYPE
    SYNTAX      Unsigned32
    UNITS       "bps"
    MAX-ACCESS  read-write
    STATUS      current
    DESCRIPTION
        "TS input rate in bps used with a constant bitrate input traffic profile.
        Current devices support a range of 10 to 250000000 bps."
    DEFVAL { 1000000 }
    ::= { ntcProtTsOIpInConfEntry 14 }
    
ntcProtTsOIpInCounterReset       OBJECT-TYPE
    SYNTAX      INTEGER { counting(0), reset(1) }
    MAX-ACCESS  read-write
    STATUS      current
    DESCRIPTION
        "Reset the TS over IP traffic and monitor counters."
    DEFVAL { counting }
    ::= { ntcProtTsOIpInMon 1 }
    
ntcProtTsOIpInMInpSelTsBRate     OBJECT-TYPE
    SYNTAX      Unsigned32
    UNITS       "bps"
    MAX-ACCESS  read-only
    STATUS      current
    DESCRIPTION
        "Displays the measured TS over IP input TS bit rate in bps."
    ::= { ntcProtTsOIpInMon 2 }
    
ntcProtTsOIpInSwitchCount        OBJECT-TYPE
    SYNTAX      Counter32
    MAX-ACCESS  read-only
    STATUS      current
    DESCRIPTION
        "Counts the number of times the device switched to another TS input."
    ::= { ntcProtTsOIpInMon 3 }
    
ntcProtTsOIpInActiveInput        OBJECT-TYPE
    SYNTAX      INTEGER { none(0), tsoip1(1), tsoip2(2) }
    MAX-ACCESS  read-only
    STATUS      current
    DESCRIPTION
        "Currently selected input by the protected port."
    ::= { ntcProtTsOIpInMon 4 }
    
ntcProtTsOIpInMonTable           OBJECT-TYPE
    SYNTAX      SEQUENCE OF NtcProtTsOIpInMonEntry
    MAX-ACCESS  not-accessible
    STATUS      current
    DESCRIPTION
        "Monitoring table"
    ::= { ntcProtTsOIpInMon 5 }

ntcProtTsOIpInMonEntry           OBJECT-TYPE
    SYNTAX      NtcProtTsOIpInMonEntry
    MAX-ACCESS  not-accessible
    STATUS      current
    DESCRIPTION
        "A conceptual row of the ntcProtTsOIpInMonTable."
    INDEX   { ntcProtTsOIpInMonName  }
    ::= { ntcProtTsOIpInMonTable 1 }

NtcProtTsOIpInMonEntry           ::= SEQUENCE {
    ntcProtTsOIpInMonName               DisplayString,
    ntcProtTsOIpInMonMeasInTsBitRate    Unsigned32,
    ntcProtTsOIpInMonBufferDelay        Unsigned32,
    ntcProtTsOIpInMonMinBufferFill      Unsigned32,
    ntcProtTsOIpInMonMaxBufferFill      Unsigned32,
    ntcProtTsOIpInMonSourceInfo         DisplayString,
    ntcProtTsOIpInMonRtpFecScheme       DisplayString,
    ntcProtTsOIpInMonTsInCount          Counter32,
    ntcProtTsOIpInMonRtpInCount         Counter32,
    ntcProtTsOIpInMonRtpColFecInCnt     Counter32,
    ntcProtTsOIpInMonRtpRowFecInCnt     Counter32,
    ntcProtTsOIpInMonTsOutCount         Counter32,
    ntcProtTsOIpInMonTsDropCount        Counter32,
    ntcProtTsOIpInMonTsOverflowCount    Counter32,
    ntcProtTsOIpInMonRtpDropCount       Counter32,
    ntcProtTsOIpInMonRtpFecDropCount    Counter32,
    ntcProtTsOIpInMonRtpRepairCount     Counter32,
    ntcProtTsOIpInActivePcrPid          Unsigned32
    }
    
ntcProtTsOIpInMonName            OBJECT-TYPE
    SYNTAX      DisplayString (SIZE(0..32))
    MAX-ACCESS  not-accessible
    STATUS      current
    DESCRIPTION
        "Name of the output monitor"
    ::= { ntcProtTsOIpInMonEntry 1 }
    
ntcProtTsOIpInMonMeasInTsBitRate OBJECT-TYPE
    SYNTAX      Unsigned32
    UNITS       "bps"
    MAX-ACCESS  read-only
    STATUS      current
    DESCRIPTION
        "Displays the measured TS over IP input TS bit rate in bps."
    ::= { ntcProtTsOIpInMonEntry 2 }
    
ntcProtTsOIpInMonBufferDelay     OBJECT-TYPE
    SYNTAX      Unsigned32
    UNITS       "ms"
    MAX-ACCESS  read-only
    STATUS      current
    DESCRIPTION
        "The delay introduced by the device to compensate the jitter introduced by the
        IP network. This is only relevant for CBR traffic."
    ::= { ntcProtTsOIpInMonEntry 3 }
    
ntcProtTsOIpInMonMinBufferFill   OBJECT-TYPE
    SYNTAX      Unsigned32
    UNITS       "ms"
    MAX-ACCESS  read-only
    STATUS      current
    DESCRIPTION
        "The measured minimum buffer delay in the buffer which compensate the jitter of
        the IP network. This is only relevant for CBR traffic."
    ::= { ntcProtTsOIpInMonEntry 4 }
    
ntcProtTsOIpInMonMaxBufferFill   OBJECT-TYPE
    SYNTAX      Unsigned32
    UNITS       "ms"
    MAX-ACCESS  read-only
    STATUS      current
    DESCRIPTION
        "The measured maximum buffer delay in the buffer which compensate the jitter of
        the IP network. This is only relevant for CBR traffic."
    ::= { ntcProtTsOIpInMonEntry 5 }
    
ntcProtTsOIpInMonSourceInfo      OBJECT-TYPE
    SYNTAX      DisplayString (SIZE(0..32))
    MAX-ACCESS  read-only
    STATUS      current
    DESCRIPTION
        "Displays the IP address (and UDP port) of the source that is generating the TS
        over IP traffic."
    ::= { ntcProtTsOIpInMonEntry 6 }
    
ntcProtTsOIpInMonRtpFecScheme    OBJECT-TYPE
    SYNTAX      DisplayString (SIZE(0..32))
    MAX-ACCESS  read-only
    STATUS      current
    DESCRIPTION
        "Displays the type of Rtp FEC Scheme currently used (if any)."
    ::= { ntcProtTsOIpInMonEntry 7 }
    
ntcProtTsOIpInMonTsInCount       OBJECT-TYPE
    SYNTAX      Counter32
    UNITS       "packets"
    MAX-ACCESS  read-only
    STATUS      current
    DESCRIPTION
        "Displays the Number of received TS packets in UDP mode."
    ::= { ntcProtTsOIpInMonEntry 8 }
    
ntcProtTsOIpInMonRtpInCount      OBJECT-TYPE
    SYNTAX      Counter32
    UNITS       "packets"
    MAX-ACCESS  read-only
    STATUS      current
    DESCRIPTION
        "Displays the number of received RTP packets. (only applicable when RTP is
        used)"
    ::= { ntcProtTsOIpInMonEntry 9 }
    
ntcProtTsOIpInMonRtpColFecInCnt  OBJECT-TYPE
    SYNTAX      Counter32
    UNITS       "packets"
    MAX-ACCESS  read-only
    STATUS      current
    DESCRIPTION
        "Displays the number of received (input) RTP column FEC packets."
    ::= { ntcProtTsOIpInMonEntry 10 }
    
ntcProtTsOIpInMonRtpRowFecInCnt  OBJECT-TYPE
    SYNTAX      Counter32
    UNITS       "packets"
    MAX-ACCESS  read-only
    STATUS      current
    DESCRIPTION
        "Displays the number of received RTP row FEC packets. (Only applicable when RTP
        with FEC is used.)"
    ::= { ntcProtTsOIpInMonEntry 11 }
    
ntcProtTsOIpInMonTsOutCount      OBJECT-TYPE
    SYNTAX      Counter32
    UNITS       "packets"
    MAX-ACCESS  read-only
    STATUS      current
    DESCRIPTION
        "Displays the number of valid TS packets leaving the TS over IP input
        processing."
    ::= { ntcProtTsOIpInMonEntry 12 }
    
ntcProtTsOIpInMonTsDropCount     OBJECT-TYPE
    SYNTAX      Counter32
    UNITS       "packets"
    MAX-ACCESS  read-only
    STATUS      current
    DESCRIPTION
        "Number of dropped TS packets. (When RTP is used the number of dropped TS
        packets in the RTP frame is counted.)"
    ::= { ntcProtTsOIpInMonEntry 13 }
    
ntcProtTsOIpInMonTsOverflowCount OBJECT-TYPE
    SYNTAX      Counter32
    UNITS       "packets"
    MAX-ACCESS  read-only
    STATUS      current
    DESCRIPTION
        "Displays the number of TS packets that are dropped because of an overflow
        situation."
    ::= { ntcProtTsOIpInMonEntry 14 }
    
ntcProtTsOIpInMonRtpDropCount    OBJECT-TYPE
    SYNTAX      Counter32
    UNITS       "packets"
    MAX-ACCESS  read-only
    STATUS      current
    DESCRIPTION
        "Displays the number of dropped RTP packets. (This is only applicable when RTP
        is used.)"
    ::= { ntcProtTsOIpInMonEntry 15 }
    
ntcProtTsOIpInMonRtpFecDropCount OBJECT-TYPE
    SYNTAX      Counter32
    UNITS       "packets"
    MAX-ACCESS  read-only
    STATUS      current
    DESCRIPTION
        "Displays the number of dropped uncorrectable packets. (This is only applicable
        when RTP-FEC is used.)"
    ::= { ntcProtTsOIpInMonEntry 16 }
    
ntcProtTsOIpInMonRtpRepairCount  OBJECT-TYPE
    SYNTAX      Counter32
    UNITS       "packets"
    MAX-ACCESS  read-only
    STATUS      current
    DESCRIPTION
        "Displays the number of repaired RTP packets by using the received FEC
        information. (This is only applicable for RTP with FEC)"
    ::= { ntcProtTsOIpInMonEntry 17 }
    
ntcProtTsOIpInActivePcrPid       OBJECT-TYPE
    SYNTAX      Unsigned32 (0..8190)
    MAX-ACCESS  read-only
    STATUS      current
    DESCRIPTION
        "Active PCR PID."
    ::= { ntcProtTsOIpInMonEntry 18 }
    
ntcProtTsOIpInAlarmStatusTable   OBJECT-TYPE
    SYNTAX      SEQUENCE OF NtcProtTsOIpInAlarmStatusEntry
    MAX-ACCESS  not-accessible
    STATUS      current
    DESCRIPTION
        "Alarm status table"
    ::= { ntcProtTsOIpInAlarms 1 }

ntcProtTsOIpInAlarmStatusEntry   OBJECT-TYPE
    SYNTAX      NtcProtTsOIpInAlarmStatusEntry
    MAX-ACCESS  not-accessible
    STATUS      current
    DESCRIPTION
        "A conceptual row of the ntcProtTsOIpInAlarmStatusTable."
    INDEX   { ntcProtTsOIpInAlarmStatusName  }
    ::= { ntcProtTsOIpInAlarmStatusTable 1 }

NtcProtTsOIpInAlarmStatusEntry   ::= SEQUENCE {
    ntcProtTsOIpInAlarmStatusName    DisplayString,
    ntcProtTsOIpInNoInputData        NtcAlarmState,
    ntcProtTsOIpInBufferUnderflow    NtcAlarmState,
    ntcProtTsOIpInBufferOverflow     NtcAlarmState,
    ntcProtTsOIpInRtpNoSync          NtcAlarmState
    }
    
ntcProtTsOIpInAlarmStatusName    OBJECT-TYPE
    SYNTAX      DisplayString (SIZE(0..32))
    MAX-ACCESS  not-accessible
    STATUS      current
    DESCRIPTION
        "Name of the alarm monitor"
    ::= { ntcProtTsOIpInAlarmStatusEntry 1 }
    
ntcProtTsOIpInNoInputData        OBJECT-TYPE
    SYNTAX      NtcAlarmState
    MAX-ACCESS  read-only
    STATUS      current
    DESCRIPTION
        "This alarm is raised when no input data is received for at least one of the
        the redundant TS over IP inputs. This variable indicates the current status of
        the alarm."
    ::= { ntcProtTsOIpInAlarmStatusEntry 2 }
    
ntcProtTsOIpInBufferUnderflow    OBJECT-TYPE
    SYNTAX      NtcAlarmState
    MAX-ACCESS  read-only
    STATUS      current
    DESCRIPTION
        "This alarm is raised when the input data buffer is below the minimum value.
        This variable indicates the current status of the alarm."
    ::= { ntcProtTsOIpInAlarmStatusEntry 3 }
    
ntcProtTsOIpInBufferOverflow     OBJECT-TYPE
    SYNTAX      NtcAlarmState
    MAX-ACCESS  read-only
    STATUS      current
    DESCRIPTION
        "This alarm is raised when the input data buffer of TS over IP is full. This
        variable indicates the current status of the alarm."
    ::= { ntcProtTsOIpInAlarmStatusEntry 4 }
    
ntcProtTsOIpInRtpNoSync          OBJECT-TYPE
    SYNTAX      NtcAlarmState
    MAX-ACCESS  read-only
    STATUS      current
    DESCRIPTION
        "This alarm is raised when no valid RTP input data is received. This variable
        indicates the current status of the alarm."
    ::= { ntcProtTsOIpInAlarmStatusEntry 5 }
    
ntcProtTsOIpInAlRedFailure       OBJECT-TYPE
    SYNTAX      NtcAlarmState
    MAX-ACCESS  read-only
    STATUS      current
    DESCRIPTION
        "This alarm is raised when a failure in redundancy is detected on a protected
        TSoIP input interface. This variable indicates the current status of the
        alarm."
    ::= { ntcProtTsOIpInAlarm 1 }
    
ntcProtTsOIpInAlRedDegraded      OBJECT-TYPE
    SYNTAX      NtcAlarmState
    MAX-ACCESS  read-only
    STATUS      current
    DESCRIPTION
        "This alarm is raised when one of the interface of a redundant TSoIP input
        interface is down. This variable indicates the current status of the alarm."
    ::= { ntcProtTsOIpInAlarm 2 }
    
ntcProtTsOIpInAlNoInputData      OBJECT-TYPE
    SYNTAX      NtcAlarmState
    MAX-ACCESS  read-only
    STATUS      current
    DESCRIPTION
        "This alarm is raised when no input data is received for at least one of the
        the redundant TS over IP inputs. This variable indicates the current status of
        the alarm."
    ::= { ntcProtTsOIpInAlarm 3 }
    
ntcProtTsOIpInAlBufferUnderflow  OBJECT-TYPE
    SYNTAX      NtcAlarmState
    MAX-ACCESS  read-only
    STATUS      current
    DESCRIPTION
        "This alarm is raised when the input data buffer is below the minimum value.
        This variable indicates the current status of the alarm."
    ::= { ntcProtTsOIpInAlarm 4 }
    
ntcProtTsOIpInAlBufferOverflow   OBJECT-TYPE
    SYNTAX      NtcAlarmState
    MAX-ACCESS  read-only
    STATUS      current
    DESCRIPTION
        "This alarm is raised when the input data buffer of TS over IP is full. This
        variable indicates the current status of the alarm."
    ::= { ntcProtTsOIpInAlarm 5 }
    
ntcProtTsOIpInAlRtpNoSync        OBJECT-TYPE
    SYNTAX      NtcAlarmState
    MAX-ACCESS  read-only
    STATUS      current
    DESCRIPTION
        "This alarm is raised when no valid RTP input data is received. This variable
        indicates the current status of the alarm."
    ::= { ntcProtTsOIpInAlarm 6 }
    

--
--  Module Conformance
--

ntcProtTsOIpInConfGrpV1Standard  OBJECT-GROUP
    OBJECTS    {
                   ntcProtTsOIpInEnable,
                   ntcProtTsOIpInProtInpSelection,
                   ntcProtTsOIpInInpSelection,
                   ntcProtTsOIpInTsEncapProtocol,
                   ntcProtTsOIpInIpAddressType,
                   ntcProtTsOIpInMulticastAddress,
                   ntcProtTsOIpInMulticastSourceA,
                   ntcProtTsOIpInMulticastSourceB,
                   ntcProtTsOIpInUdpPort,
                   ntcProtTsOIpInTrafficProfile,
                   ntcProtTsOIpInInputRateType,
                   ntcProtTsOIpInAutoPcrDetection,
                   ntcProtTsOIpInPcrPid,
                   ntcProtTsOIpInMaxBufferDelay,
                   ntcProtTsOIpInInputTsBitRate,
                   ntcProtTsOIpInCounterReset,
                   ntcProtTsOIpInMInpSelTsBRate,
                   ntcProtTsOIpInSwitchCount,
                   ntcProtTsOIpInActiveInput,
                   ntcProtTsOIpInMonMeasInTsBitRate,
                   ntcProtTsOIpInMonBufferDelay,
                   ntcProtTsOIpInMonMinBufferFill,
                   ntcProtTsOIpInMonMaxBufferFill,
                   ntcProtTsOIpInMonSourceInfo,
                   ntcProtTsOIpInMonRtpFecScheme,
                   ntcProtTsOIpInMonTsInCount,
                   ntcProtTsOIpInMonRtpInCount,
                   ntcProtTsOIpInMonRtpColFecInCnt,
                   ntcProtTsOIpInMonRtpRowFecInCnt,
                   ntcProtTsOIpInMonTsOutCount,
                   ntcProtTsOIpInMonTsDropCount,
                   ntcProtTsOIpInMonTsOverflowCount,
                   ntcProtTsOIpInMonRtpDropCount,
                   ntcProtTsOIpInMonRtpFecDropCount,
                   ntcProtTsOIpInMonRtpRepairCount,
                   ntcProtTsOIpInActivePcrPid,
                   ntcProtTsOIpInNoInputData,
                   ntcProtTsOIpInBufferUnderflow,
                   ntcProtTsOIpInBufferOverflow,
                   ntcProtTsOIpInRtpNoSync,
                   ntcProtTsOIpInAlRedFailure,
                   ntcProtTsOIpInAlRedDegraded,
                   ntcProtTsOIpInAlNoInputData,
                   ntcProtTsOIpInAlBufferUnderflow,
                   ntcProtTsOIpInAlBufferOverflow,
                   ntcProtTsOIpInAlRtpNoSync
               }
    STATUS      current
    DESCRIPTION
        "Managed objects that constitute version 1 of a system device with standard capabilities."
    ::= { ntcProtTsOIpInConfGroup 1}
    
ntcProtTsOIpInConfCompV1Standard MODULE-COMPLIANCE
    STATUS      current
    DESCRIPTION
        "Compliance statement for Newtec device MIB implementations."
    MODULE  -- this module
    MANDATORY-GROUPS
                  {
                      ntcProtTsOIpInConfGrpV1Standard
                  }
    ::= { ntcProtTsOIpInConfCompliance  1 }
    

END
