NEWTEC-SIMPEDECAPS-MIB DEFINITIONS ::= BEGIN

IMPORTS
    Unsigned32,
    Counter64,
    MODULE-IDENTITY,
    OBJECT-IDENTITY,
    OBJECT-TYPE
        FROM SNMPv2-SMI

    MODULE-COMPLIANCE,
    OBJECT-GROUP
        FROM SNMPv2-CONF
    
    NtcAlarmState,
    NtcEnable
        FROM NEWTEC-TC-MIB

    MacAddress
        FROM SNMPv2-TC

    ntcFunction
        FROM NEWTEC-MAIN-MIB;


--
--  Module Identification
--

ntcSiMpeDecaps   MODULE-IDENTITY
    LAST-UPDATED "201409090900Z"
    ORGANIZATION "Newtec Cy"
    CONTACT-INFO
        "Newtec Cy
         Postal: Newtec Cy
                 Laarstraat 5
                 B-9100 Sint-Niklaas
                 Belgium

                Tel: +32 3 780 65 00
                Fax: +32 3 780 65 49
                Web: www.newtec.be
                E-mail: techsupport@newtec.be"
    DESCRIPTION
        "Newtec modular MIB containing definitions for MPE decaps functionality."

    REVISION  "201409090900Z"
    DESCRIPTION
        "Initial release for M6100-2.5"
    ::= { ntcFunction  8500 }
    

--
-- Top-Level Structure
--

-- ntcSiMpeDecaps content

ntcSiMpeDeObjects                OBJECT-IDENTITY
    STATUS        current
    DESCRIPTION   "Container holding ntcSiMpeDeObjects definitions."
    ::= { ntcSiMpeDecaps 1 }
    
ntcSiMpeDeConformance            OBJECT-IDENTITY
    STATUS        current
    DESCRIPTION   "Conformance requirements."
    ::= { ntcSiMpeDecaps 2 }
    
-- ntcSiMpeDeObjects content

ntcSiMpeDeConfiguration          OBJECT-IDENTITY
    STATUS        current
    DESCRIPTION   "Container holding ntcSiMpeDeConfiguration definitions."
    ::= { ntcSiMpeDeObjects 1 }
    
ntcSiMpeDeMonitoring             OBJECT-IDENTITY
    STATUS        current
    DESCRIPTION   "Container holding ntcSiMpeDeMonitoring definitions."
    ::= { ntcSiMpeDeObjects 2 }
    
ntcSiMpeDeAlarms                 OBJECT-IDENTITY
    STATUS        current
    DESCRIPTION   "Container holding ntcSiMpeDeAlarms definitions."
    ::= { ntcSiMpeDeObjects 3 }
    
-- ntcSiMpeDeConformance content

ntcSiMpeDeConfCompliance         OBJECT-IDENTITY
    STATUS        current
    DESCRIPTION   "Device compliance statements."
    ::= { ntcSiMpeDeConformance 1 }
    
ntcSiMpeDeConfGroup              OBJECT-IDENTITY
    STATUS        current
    DESCRIPTION   "Groups used by device compliance statements."
    ::= { ntcSiMpeDeConformance 2 }
    

--
-- Managed Objects
--

ntcSiMpeDeEnable                 OBJECT-TYPE
    SYNTAX      NtcEnable
    MAX-ACCESS  read-write
    STATUS      current
    DESCRIPTION
        "Enable or disable the MPE decapsulation."
    DEFVAL { off }
    ::= { ntcSiMpeDeConfiguration 1 }
    
ntcSiMpeDeDataPid                OBJECT-TYPE
    SYNTAX      Unsigned32 (32..8190)
    MAX-ACCESS  read-write
    STATUS      current
    DESCRIPTION
        "The MPEG2 TS Packet Identifier (PID) used for the MPE encapsulated data."
    DEFVAL { 3000 }
    ::= { ntcSiMpeDeConfiguration 2 }
    
ntcSiMpeDeMacAddress             OBJECT-TYPE
    SYNTAX      MacAddress
    MAX-ACCESS  read-write
    STATUS      current
    DESCRIPTION
        "Mac address of the destination channel."
    DEFVAL { "00:00:00:00:00:00" }
    ::= { ntcSiMpeDeConfiguration 3 }
    
ntcSiMpeDeCounterReset           OBJECT-TYPE
    SYNTAX      INTEGER { counting(0), reset(1) }
    MAX-ACCESS  read-write
    STATUS      current
    DESCRIPTION
        "Reset the MPE decapsulation monitor counters."
    DEFVAL { counting }
    ::= { ntcSiMpeDeMonitoring 1 }
    
ntcSiMpeDeForwardBitRate         OBJECT-TYPE
    SYNTAX      Counter64
    UNITS       "bps"
    MAX-ACCESS  read-only
    STATUS      current
    DESCRIPTION
        "MPE forwarding bit rate (bits/s)."
    ::= { ntcSiMpeDeMonitoring 2 }
    
ntcSiMpeDeDroppedPackets         OBJECT-TYPE
    SYNTAX      Counter64
    UNITS       "packets"
    MAX-ACCESS  read-only
    STATUS      current
    DESCRIPTION
        "Number of dropped packets."
    ::= { ntcSiMpeDeMonitoring 3 }
    
ntcSiMpeDeAlDataOverflow         OBJECT-TYPE
    SYNTAX      NtcAlarmState
    MAX-ACCESS  read-only
    STATUS      current
    DESCRIPTION
        "This alarm is raised when the bitrate send out is higher than the max possible
        for the given interface. This variable indicates the current status of the
        alarm."
    ::= { ntcSiMpeDeAlarms 1 }
    

--
--  Module Conformance
--

ntcSiMpeDeConfGrpV1Standard      OBJECT-GROUP
    OBJECTS    {
                   ntcSiMpeDeEnable,
                   ntcSiMpeDeDataPid,
                   ntcSiMpeDeMacAddress,
                   ntcSiMpeDeCounterReset,
                   ntcSiMpeDeForwardBitRate,
                   ntcSiMpeDeDroppedPackets,
                   ntcSiMpeDeAlDataOverflow
               }
    STATUS      current
    DESCRIPTION
        "Managed objects that constitute version 1 of a system device with standard capabilities."
    ::= { ntcSiMpeDeConfGroup 1}
    
ntcSiMpeDeConfCompV1Standard     MODULE-COMPLIANCE
    STATUS      current
    DESCRIPTION
        "Compliance statement for Newtec device MIB implementations."
    MODULE  -- this module
    MANDATORY-GROUPS
                  {
                      ntcSiMpeDeConfGrpV1Standard
                  }
    ::= { ntcSiMpeDeConfCompliance  1 }
    

END
